AddReference "ModulesForm.dll"
AddReference "System.Collections"
AddReference "System.Core"
AddReference "System.Linq"
AddReference "System.XML"

Imports Inventor
Imports System.IO
Imports System.Core
Imports System.Linq
Imports System.Windows.Forms
Imports System.Collections
Imports System.Collections.Generic
Imports System.XML

Public Sub Main()
    If Not RuleArguments.Exists("Filename") Then
        'RunGetModuleConfig("C:\path\to\excel\data\file.xlsx")
        'iLogicForm.ShowGlobal("Form 1", FormMode.NonModal) 'doesn't allow for passing of variables to the form!
        Using dlg As New ModulesForm.Form1
            dlg.Showdialog()

        End Using

    Else 'being run from the helper rules.

    End If

End Sub
#Region "Modules class created from modules.xsd file."
Public Class Modules
    '' ------------------------------------------------------------------------------
    ''  <auto-generated>
    ''    Generated by Xsd2Code. Version 3.4.0.32989
    ''    <NameSpace>Power_Pack_For_Inventor_AddIn</NameSpace><Collection>List</Collection><codeType>VisualBasic</codeType><EnableDataBinding>False</EnableDataBinding><EnableLazyLoading>False</EnableLazyLoading><TrackingChangesEnable>False</TrackingChangesEnable><GenTrackingClasses>False</GenTrackingClasses><HidePrivateFieldInIDE>False</HidePrivateFieldInIDE><EnableSummaryComment>True</EnableSummaryComment><VirtualProp>False</VirtualProp><IncludeSerializeMethod>True</IncludeSerializeMethod><UseBaseClass>True</UseBaseClass><GenBaseClass>True</GenBaseClass><GenerateCloneMethod>False</GenerateCloneMethod><GenerateDataContracts>False</GenerateDataContracts><CodeBaseTag>Net20</CodeBaseTag><SerializeMethodName>Serialize</SerializeMethodName><DeserializeMethodName>Deserialize</DeserializeMethodName><SaveToFileMethodName>SaveToFile</SaveToFileMethodName><LoadFromFileMethodName>LoadFromFile</LoadFromFileMethodName><GenerateXMLAttributes>True</GenerateXMLAttributes><OrderXMLAttrib>False</OrderXMLAttrib><EnableEncoding>False</EnableEncoding><AutomaticProperties>False</AutomaticProperties><GenerateShouldSerialize>False</GenerateShouldSerialize><DisableDebug>False</DisableDebug><PropNameSpecified>Default</PropNameSpecified><Encoder>UTF8</Encoder><CustomUsings></CustomUsings><ExcludeIncludedTypes>False</ExcludeIncludedTypes><EnableInitializeFields>True</EnableInitializeFields>
    ''  </auto-generated>
    '' ------------------------------------------------------------------------------


#Region "Base entity class"
    Partial Public Class EntityBase(Of T)

        Private Shared sSerializer As System.Xml.Serialization.XmlSerializer

        Private Shared ReadOnly Property Serializer() As System.Xml.Serialization.XmlSerializer
            Get
                If (sSerializer Is Nothing) Then
                    sSerializer = New System.Xml.Serialization.XmlSerializer(GetType(T))
                End If
                Return sSerializer
            End Get
        End Property

#Region "Serialize/Deserialize"
        '''<summary>
        '''Serializes current EntityBase object into an XML document
        '''</summary>
        '''<returns>string XML value</returns>
        Public Overridable Function Serialize() As String
            Dim streamReader As System.IO.StreamReader = Nothing
            Dim memoryStream As System.IO.MemoryStream = Nothing
            Try
                memoryStream = New System.IO.MemoryStream
                Serializer.Serialize(memoryStream, Me)
                memoryStream.Seek(0, System.IO.SeekOrigin.Begin)
                streamReader = New System.IO.StreamReader(memoryStream)
                Return streamReader.ReadToEnd
            Finally
                If (Not (streamReader) Is Nothing) Then
                    streamReader.Dispose()
                End If
                If (Not (memoryStream) Is Nothing) Then
                    memoryStream.Dispose()
                End If
            End Try
        End Function

        '''<summary>
        '''Deserializes workflow markup into an EntityBase object
        '''</summary>
        '''<param name="xml">string workflow markup to deserialize</param>
        '''<param name="obj">Output EntityBase object</param>
        '''<param name="exception">output Exception value if deserialize failed</param>
        '''<returns>true if this XmlSerializer can deserialize the object; otherwise, false</returns>
        Public Overloads Shared Function Deserialize(ByVal xml As String, ByRef obj As T, ByRef exception As System.Exception) As Boolean
            exception = Nothing
            obj = CType(Nothing, T)
            Try
                obj = Deserialize(xml)
                Return True
            Catch ex As System.Exception
                exception = ex
                Return False
            End Try
        End Function

        Public Overloads Shared Function Deserialize(ByVal xml As String, ByRef obj As T) As Boolean
            Dim exception As System.Exception = Nothing
            Return Deserialize(xml, obj, exception)
        End Function

        Public Overloads Shared Function Deserialize(ByVal xml As String) As T
            Dim stringReader As System.IO.StringReader = Nothing
            Try
                stringReader = New System.IO.StringReader(xml)
                Return CType(Serializer.Deserialize(System.Xml.XmlReader.Create(stringReader)), T)
            Finally
                If (Not (stringReader) Is Nothing) Then
                    stringReader.Dispose()
                End If
            End Try
        End Function

        '''<summary>
        '''Serializes current EntityBase object into file
        '''</summary>
        '''<param name="fileName">full path of outupt xml file</param>
        '''<param name="exception">output Exception value if failed</param>
        '''<returns>true if can serialize and save into file; otherwise, false</returns>
        Public Overridable Overloads Function SaveToFile(ByVal fileName As String, ByRef exception As System.Exception) As Boolean
            exception = Nothing
            Try
                SaveToFile(fileName)
                Return True
            Catch e As System.Exception
                exception = e
                Return False
            End Try
        End Function

        Public Overridable Overloads Sub SaveToFile(ByVal fileName As String)
            Dim streamWriter As System.IO.StreamWriter = Nothing
            Try
                Dim xmlString As String = Serialize()
                Dim xmlFile As System.IO.FileInfo = New System.IO.FileInfo(fileName)
                streamWriter = xmlFile.CreateText
                streamWriter.WriteLine(xmlString)
                streamWriter.Close()
            Finally
                If (Not (streamWriter) Is Nothing) Then
                    streamWriter.Dispose()
                End If
            End Try
        End Sub

        '''<summary>
        '''Deserializes xml markup from file into an EntityBase object
        '''</summary>
        '''<param name="fileName">string xml file to load and deserialize</param>
        '''<param name="obj">Output EntityBase object</param>
        '''<param name="exception">output Exception value if deserialize failed</param>
        '''<returns>true if this XmlSerializer can deserialize the object; otherwise, false</returns>
        Public Overloads Shared Function LoadFromFile(ByVal fileName As String, ByRef obj As T, ByRef exception As System.Exception) As Boolean
            exception = Nothing
            obj = CType(Nothing, T)
            Try
                obj = LoadFromFile(fileName)
                Return True
            Catch ex As System.Exception
                exception = ex
                Return False
            End Try
        End Function

        Public Overloads Shared Function LoadFromFile(ByVal fileName As String, ByRef obj As T) As Boolean
            Dim exception As System.Exception = Nothing
            Return LoadFromFile(fileName, obj, exception)
        End Function

        Public Overloads Shared Function LoadFromFile(ByVal fileName As String) As T
            Dim file As System.IO.FileStream = Nothing
            Dim sr As System.IO.StreamReader = Nothing
            Try
                file = New System.IO.FileStream(fileName, FileMode.Open, FileAccess.Read)
                sr = New System.IO.StreamReader(file)
                Dim xmlString As String = sr.ReadToEnd
                sr.Close()
                file.Close()
                Return Deserialize(xmlString)
            Finally
                If (Not (file) Is Nothing) Then
                    file.Dispose()
                End If
                If (Not (sr) Is Nothing) Then
                    sr.Dispose()
                End If
            End Try
        End Function
#End Region
    End Class
#End Region

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute("root", [Namespace]:="http://tempuri.org/Modules.xsd", IsNullable:=False)>
    Partial Public Class FilterHouseVariants
        Inherits EntityBase(Of FilterHouseVariants)

        Private fHOptionField As List(Of FilterHouse)

        '''<summary>
        '''FilterHouseVariants class constructor
        '''</summary>
        Public Sub New()
            MyBase.New
            Me.fHOptionField = New List(Of FilterHouse)
        End Sub

        <System.Xml.Serialization.XmlElementAttribute("FHOption")>
        Public Property FHOption() As List(Of FilterHouse)
            Get
                Return Me.fHOptionField
            End Get
            Set
                Me.fHOptionField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class FilterHouse
        Inherits EntityBase(Of FilterHouse)

        Private doorsField As List(Of FilterHouseDoorType)

        Private leftModulesField As List(Of ModuleType)

        Private rightModulesField As List(Of ModuleType)

        Private transitionField As TransitionType

        Private externalDrainageField As MiscSystemType

        Private inletFlangePatternField As MiscSystemType

        Private outletFlangePatternField As MiscSystemType

        Private shimPackField As MiscSystemType

        Private cablingField As MiscSystemType

        Private numFiltersHighField As String

        Private numFiltersWideField As String

        Private numFiltrationStagesField As String

        '''<summary>
        '''FilterHouse class constructor
        '''</summary>
        Public Sub New()
            MyBase.New
            Me.cablingField = New MiscSystemType
            Me.shimPackField = New MiscSystemType
            Me.outletFlangePatternField = New MiscSystemType
            Me.inletFlangePatternField = New MiscSystemType
            Me.externalDrainageField = New MiscSystemType
            Me.transitionField = New TransitionType
            Me.rightModulesField = New List(Of ModuleType)
            Me.leftModulesField = New List(Of ModuleType)
            Me.doorsField = New List(Of FilterHouseDoorType)
        End Sub

        <System.Xml.Serialization.XmlArrayItemAttribute("door", IsNullable:=False)>
        Public Property Doors() As List(Of FilterHouseDoorType)
            Get
                Return Me.doorsField
            End Get
            Set
                Me.doorsField = Value
            End Set
        End Property

        <System.Xml.Serialization.XmlArrayItemAttribute("Module", IsNullable:=False)>
        Public Property LeftModules() As List(Of ModuleType)
            Get
                Return Me.leftModulesField
            End Get
            Set
                Me.leftModulesField = Value
            End Set
        End Property

        <System.Xml.Serialization.XmlArrayItemAttribute("Module", IsNullable:=False)>
        Public Property RightModules() As List(Of ModuleType)
            Get
                Return Me.rightModulesField
            End Get
            Set
                Me.rightModulesField = Value
            End Set
        End Property

        Public Property Transition() As TransitionType
            Get
                Return Me.transitionField
            End Get
            Set
                Me.transitionField = Value
            End Set
        End Property

        Public Property ExternalDrainage() As MiscSystemType
            Get
                Return Me.externalDrainageField
            End Get
            Set
                Me.externalDrainageField = Value
            End Set
        End Property

        Public Property InletFlangePattern() As MiscSystemType
            Get
                Return Me.inletFlangePatternField
            End Get
            Set
                Me.inletFlangePatternField = Value
            End Set
        End Property

        Public Property OutletFlangePattern() As MiscSystemType
            Get
                Return Me.outletFlangePatternField
            End Get
            Set
                Me.outletFlangePatternField = Value
            End Set
        End Property

        Public Property ShimPack() As MiscSystemType
            Get
                Return Me.shimPackField
            End Get
            Set
                Me.shimPackField = Value
            End Set
        End Property

        Public Property Cabling() As MiscSystemType
            Get
                Return Me.cablingField
            End Get
            Set
                Me.cablingField = Value
            End Set
        End Property

        <System.Xml.Serialization.XmlAttributeAttribute(DataType:="integer")>
        Public Property NumFiltersHigh() As String
            Get
                Return Me.numFiltersHighField
            End Get
            Set
                Me.numFiltersHighField = Value
            End Set
        End Property

        <System.Xml.Serialization.XmlAttributeAttribute(DataType:="integer")>
        Public Property NumFiltersWide() As String
            Get
                Return Me.numFiltersWideField
            End Get
            Set
                Me.numFiltersWideField = Value
            End Set
        End Property

        <System.Xml.Serialization.XmlAttributeAttribute(DataType:="integer")>
        Public Property NumFiltrationStages() As String
            Get
                Return Me.numFiltrationStagesField
            End Get
            Set
                Me.numFiltrationStagesField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class FilterHouseDoorType
        Inherits EntityBase(Of FilterHouseDoorType)

        Private visionPanelsField As List(Of VisionPanelType)

        Private handlesField As FilterHouseDoorTypeHandles

        Private corrosionCouponsField As FilterHouseDoorTypeCorrosionCoupons

        Private parentHouseIDField As String

        Private rightHandedFrontField As Boolean

        Private rightHandedFrontFieldSpecified As Boolean

        Private leftHandedFrontField As Boolean

        Private leftHandedFrontFieldSpecified As Boolean

        Private rightHandedRearField As Boolean

        Private rightHandedRearFieldSpecified As Boolean

        Private leftHandedRearField As Boolean

        Private leftHandedRearFieldSpecified As Boolean

        Private leftHandLocationField As Boolean

        Private leftHandLocationFieldSpecified As Boolean

        Private rightHandLocationField As Boolean

        Private rightHandLocationFieldSpecified As Boolean

        Private isBoltedShutField As Boolean

        Public Sub New()
            MyBase.New
            Me.corrosionCouponsField = New FilterHouseDoorTypeCorrosionCoupons
            Me.handlesField = New FilterHouseDoorTypeHandles
            Me.visionPanelsField = New List(Of VisionPanelType)
            Me.isBoltedShutField = False
        End Sub

        <System.Xml.Serialization.XmlArrayItemAttribute("VisionPanel", IsNullable:=False)>
        Public Property VisionPanels() As List(Of VisionPanelType)
            Get
                Return Me.visionPanelsField
            End Get
            Set
                Me.visionPanelsField = Value
            End Set
        End Property

        Public Property [Handles]() As FilterHouseDoorTypeHandles
            Get
                Return Me.handlesField
            End Get
            Set
                Me.handlesField = Value
            End Set
        End Property

        <System.Xml.Serialization.XmlElementAttribute(IsNullable:=True)>
        Public Property CorrosionCoupons() As FilterHouseDoorTypeCorrosionCoupons
            Get
                Return Me.corrosionCouponsField
            End Get
            Set
                Me.corrosionCouponsField = Value
            End Set
        End Property

        <System.Xml.Serialization.XmlAttributeAttribute()>
        Public Property ParentHouseID() As String
            Get
                Return Me.parentHouseIDField
            End Get
            Set
                Me.parentHouseIDField = Value
            End Set
        End Property

        <System.Xml.Serialization.XmlAttributeAttribute()>
        Public Property RightHandedFront() As Boolean
            Get
                Return Me.rightHandedFrontField
            End Get
            Set
                Me.rightHandedFrontField = Value
            End Set
        End Property

        <System.Xml.Serialization.XmlIgnoreAttribute()>
        Public Property RightHandedFrontSpecified() As Boolean
            Get
                Return Me.rightHandedFrontFieldSpecified
            End Get
            Set
                Me.rightHandedFrontFieldSpecified = Value
            End Set
        End Property

        <System.Xml.Serialization.XmlAttributeAttribute()>
        Public Property LeftHandedFront() As Boolean
            Get
                Return Me.leftHandedFrontField
            End Get
            Set
                Me.leftHandedFrontField = Value
            End Set
        End Property

        <System.Xml.Serialization.XmlIgnoreAttribute()>
        Public Property LeftHandedFrontSpecified() As Boolean
            Get
                Return Me.leftHandedFrontFieldSpecified
            End Get
            Set
                Me.leftHandedFrontFieldSpecified = Value
            End Set
        End Property

        <System.Xml.Serialization.XmlAttributeAttribute()>
        Public Property RightHandedRear() As Boolean
            Get
                Return Me.rightHandedRearField
            End Get
            Set
                Me.rightHandedRearField = Value
            End Set
        End Property

        <System.Xml.Serialization.XmlIgnoreAttribute()>
        Public Property RightHandedRearSpecified() As Boolean
            Get
                Return Me.rightHandedRearFieldSpecified
            End Get
            Set
                Me.rightHandedRearFieldSpecified = Value
            End Set
        End Property

        <System.Xml.Serialization.XmlAttributeAttribute()>
        Public Property LeftHandedRear() As Boolean
            Get
                Return Me.leftHandedRearField
            End Get
            Set
                Me.leftHandedRearField = Value
            End Set
        End Property

        <System.Xml.Serialization.XmlIgnoreAttribute()>
        Public Property LeftHandedRearSpecified() As Boolean
            Get
                Return Me.leftHandedRearFieldSpecified
            End Get
            Set
                Me.leftHandedRearFieldSpecified = Value
            End Set
        End Property

        <System.Xml.Serialization.XmlAttributeAttribute()>
        Public Property LeftHandLocation() As Boolean
            Get
                Return Me.leftHandLocationField
            End Get
            Set
                Me.leftHandLocationField = Value
            End Set
        End Property

        <System.Xml.Serialization.XmlIgnoreAttribute()>
        Public Property LeftHandLocationSpecified() As Boolean
            Get
                Return Me.leftHandLocationFieldSpecified
            End Get
            Set
                Me.leftHandLocationFieldSpecified = Value
            End Set
        End Property

        <System.Xml.Serialization.XmlAttributeAttribute()>
        Public Property RightHandLocation() As Boolean
            Get
                Return Me.rightHandLocationField
            End Get
            Set
                Me.rightHandLocationField = Value
            End Set
        End Property

        <System.Xml.Serialization.XmlIgnoreAttribute()>
        Public Property RightHandLocationSpecified() As Boolean
            Get
                Return Me.rightHandLocationFieldSpecified
            End Get
            Set
                Me.rightHandLocationFieldSpecified = Value
            End Set
        End Property

        <System.Xml.Serialization.XmlAttributeAttribute(),
         System.ComponentModel.DefaultValueAttribute(False)>
        Public Property IsBoltedShut() As Boolean
            Get
                Return Me.isBoltedShutField
            End Get
            Set
                Me.isBoltedShutField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class VisionPanelType
        Inherits EntityBase(Of VisionPanelType)

        Private brandField As String

        Private isCircularField As Boolean

        Public Sub New()
            MyBase.New
            Me.isCircularField = True
        End Sub

        <System.Xml.Serialization.XmlAttributeAttribute()>
        Public Property Brand() As String
            Get
                Return Me.brandField
            End Get
            Set
                Me.brandField = Value
            End Set
        End Property

        <System.Xml.Serialization.XmlAttributeAttribute(),
         System.ComponentModel.DefaultValueAttribute(True)>
        Public Property IsCircular() As Boolean
            Get
                Return Me.isCircularField
            End Get
            Set
                Me.isCircularField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class TransitionSupportMemberType
        Inherits EntityBase(Of TransitionSupportMemberType)

        Private systemTypeField As String

        Private systemVersionField As String

        Private textField As List(Of String)

        '''<summary>
        '''TransitionSupportMemberType class constructor
        '''</summary>
        Public Sub New()
            MyBase.New
            Me.textField = New List(Of String)
        End Sub

        <System.Xml.Serialization.XmlAttributeAttribute()>
        Public Property SystemType() As String
            Get
                Return Me.systemTypeField
            End Get
            Set
                Me.systemTypeField = Value
            End Set
        End Property

        <System.Xml.Serialization.XmlAttributeAttribute()>
        Public Property SystemVersion() As String
            Get
                Return Me.systemVersionField
            End Get
            Set
                Me.systemVersionField = Value
            End Set
        End Property

        <System.Xml.Serialization.XmlTextAttribute()>
        Public Property Text() As List(Of String)
            Get
                Return Me.textField
            End Get
            Set
                Me.textField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class TransitionSectionType
        Inherits EntityBase(Of TransitionSectionType)

        Private systemTypeField As String

        Private systemVersionField As String

        Private textField As List(Of String)

        '''<summary>
        '''TransitionSectionType class constructor
        '''</summary>
        Public Sub New()
            MyBase.New
            Me.textField = New List(Of String)
        End Sub

        <System.Xml.Serialization.XmlAttributeAttribute()>
        Public Property SystemType() As String
            Get
                Return Me.systemTypeField
            End Get
            Set
                Me.systemTypeField = Value
            End Set
        End Property

        <System.Xml.Serialization.XmlAttributeAttribute()>
        Public Property SystemVersion() As String
            Get
                Return Me.systemVersionField
            End Get
            Set
                Me.systemVersionField = Value
            End Set
        End Property

        <System.Xml.Serialization.XmlTextAttribute()>
        Public Property Text() As List(Of String)
            Get
                Return Me.textField
            End Get
            Set
                Me.textField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class TransitionType
        Inherits EntityBase(Of TransitionType)

        Private sectionsField As List(Of TransitionSectionType)

        Private supportsField As List(Of TransitionSupportMemberType)

        Private outletOpeningWidthField As Double

        Private outletOpeningHeightField As Double

        Private outletDistanceFromFilterHouseField As Double

        Private outletDistanceFromFilterHouseBaseField As Double

        Private outletDistanceFromFilterHouseCentrelineField As Double

        Public Sub New()
            MyBase.New
            Me.supportsField = New List(Of TransitionSupportMemberType)
            Me.sectionsField = New List(Of TransitionSectionType)
            Me.outletOpeningWidthField = 13370
            Me.outletOpeningHeightField = 13370
            Me.outletDistanceFromFilterHouseField = 13370
            Me.outletDistanceFromFilterHouseBaseField = 13370
            Me.outletDistanceFromFilterHouseCentrelineField = 13370
        End Sub

        <System.Xml.Serialization.XmlArrayItemAttribute("ShellSection", IsNullable:=False)>
        Public Property sections() As List(Of TransitionSectionType)
            Get
                Return Me.sectionsField
            End Get
            Set
                Me.sectionsField = Value
            End Set
        End Property

        <System.Xml.Serialization.XmlArrayItemAttribute("SupportMember", IsNullable:=False)>
        Public Property supports() As List(Of TransitionSupportMemberType)
            Get
                Return Me.supportsField
            End Get
            Set
                Me.supportsField = Value
            End Set
        End Property

        <System.Xml.Serialization.XmlAttributeAttribute(),
         System.ComponentModel.DefaultValueAttribute(13370)>
        Public Property OutletOpeningWidth() As Double
            Get
                Return Me.outletOpeningWidthField
            End Get
            Set
                Me.outletOpeningWidthField = Value
            End Set
        End Property

        <System.Xml.Serialization.XmlAttributeAttribute(),
         System.ComponentModel.DefaultValueAttribute(13370)>
        Public Property OutletOpeningHeight() As Double
            Get
                Return Me.outletOpeningHeightField
            End Get
            Set
                Me.outletOpeningHeightField = Value
            End Set
        End Property

        <System.Xml.Serialization.XmlAttributeAttribute(),
         System.ComponentModel.DefaultValueAttribute(13370)>
        Public Property OutletDistanceFromFilterHouse() As Double
            Get
                Return Me.outletDistanceFromFilterHouseField
            End Get
            Set
                Me.outletDistanceFromFilterHouseField = Value
            End Set
        End Property

        <System.Xml.Serialization.XmlAttributeAttribute(),
         System.ComponentModel.DefaultValueAttribute(13370)>
        Public Property OutletDistanceFromFilterHouseBase() As Double
            Get
                Return Me.outletDistanceFromFilterHouseBaseField
            End Get
            Set
                Me.outletDistanceFromFilterHouseBaseField = Value
            End Set
        End Property

        <System.Xml.Serialization.XmlAttributeAttribute(),
         System.ComponentModel.DefaultValueAttribute(13370)>
        Public Property OutletDistanceFromFilterHouseCentreline() As Double
            Get
                Return Me.outletDistanceFromFilterHouseCentrelineField
            End Get
            Set
                Me.outletDistanceFromFilterHouseCentrelineField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class FilterType
        Inherits EntityBase(Of FilterType)

        Private brandField As String

        Private filterWidthField As Double

        Private filterHeightField As Double

        Private filterLengthField As Double

        Public Sub New()
            MyBase.New
            Me.brandField = "CompanyName"
            Me.filterWidthField = 610
            Me.filterHeightField = 610
            Me.filterLengthField = 1337
        End Sub

        <System.Xml.Serialization.XmlAttributeAttribute(),
         System.ComponentModel.DefaultValueAttribute("CompanyName")>
        Public Property Brand() As String
            Get
                Return Me.brandField
            End Get
            Set
                Me.brandField = Value
            End Set
        End Property

        <System.Xml.Serialization.XmlAttributeAttribute(),
         System.ComponentModel.DefaultValueAttribute(610)>
        Public Property FilterWidth() As Double
            Get
                Return Me.filterWidthField
            End Get
            Set
                Me.filterWidthField = Value
            End Set
        End Property

        <System.Xml.Serialization.XmlAttributeAttribute(),
         System.ComponentModel.DefaultValueAttribute(610)>
        Public Property FilterHeight() As Double
            Get
                Return Me.filterHeightField
            End Get
            Set
                Me.filterHeightField = Value
            End Set
        End Property

        <System.Xml.Serialization.XmlAttributeAttribute(),
         System.ComponentModel.DefaultValueAttribute(1337)>
        Public Property FilterLength() As Double
            Get
                Return Me.filterLengthField
            End Get
            Set
                Me.filterLengthField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class FModuleElement
        Inherits EntityBase(Of FModuleElement)

        Private elementIDField As String

        Private parentModuleIDField As String

        Private elementIsDisabledField As Boolean

        Private elementBracingLeftFrontField As Boolean

        Private elementBracingLeftFrontFieldSpecified As Boolean

        Private elementBracingLeftRearField As Boolean

        Private elementBracingLeftRearFieldSpecified As Boolean

        Private elementBracingRightFrontField As Boolean

        Private elementBracingRightFrontFieldSpecified As Boolean

        Private elementBracingRightRearField As Boolean

        Private elementBracingRightRearFieldSpecified As Boolean

        Private elementWidthField As String

        Public Sub New()
            MyBase.New
            Me.elementIsDisabledField = False
        End Sub

        <System.Xml.Serialization.XmlAttributeAttribute()>
        Public Property ElementID() As String
            Get
                Return Me.elementIDField
            End Get
            Set
                Me.elementIDField = Value
            End Set
        End Property

        <System.Xml.Serialization.XmlAttributeAttribute()>
        Public Property ParentModuleID() As String
            Get
                Return Me.parentModuleIDField
            End Get
            Set
                Me.parentModuleIDField = Value
            End Set
        End Property

        <System.Xml.Serialization.XmlAttributeAttribute(),
         System.ComponentModel.DefaultValueAttribute(False)>
        Public Property ElementIsDisabled() As Boolean
            Get
                Return Me.elementIsDisabledField
            End Get
            Set
                Me.elementIsDisabledField = Value
            End Set
        End Property

        <System.Xml.Serialization.XmlAttributeAttribute()>
        Public Property ElementBracingLeftFront() As Boolean
            Get
                Return Me.elementBracingLeftFrontField
            End Get
            Set
                Me.elementBracingLeftFrontField = Value
            End Set
        End Property

        <System.Xml.Serialization.XmlIgnoreAttribute()>
        Public Property ElementBracingLeftFrontSpecified() As Boolean
            Get
                Return Me.elementBracingLeftFrontFieldSpecified
            End Get
            Set
                Me.elementBracingLeftFrontFieldSpecified = Value
            End Set
        End Property

        <System.Xml.Serialization.XmlAttributeAttribute()>
        Public Property ElementBracingLeftRear() As Boolean
            Get
                Return Me.elementBracingLeftRearField
            End Get
            Set
                Me.elementBracingLeftRearField = Value
            End Set
        End Property

        <System.Xml.Serialization.XmlIgnoreAttribute()>
        Public Property ElementBracingLeftRearSpecified() As Boolean
            Get
                Return Me.elementBracingLeftRearFieldSpecified
            End Get
            Set
                Me.elementBracingLeftRearFieldSpecified = Value
            End Set
        End Property

        <System.Xml.Serialization.XmlAttributeAttribute()>
        Public Property ElementBracingRightFront() As Boolean
            Get
                Return Me.elementBracingRightFrontField
            End Get
            Set
                Me.elementBracingRightFrontField = Value
            End Set
        End Property

        <System.Xml.Serialization.XmlIgnoreAttribute()>
        Public Property ElementBracingRightFrontSpecified() As Boolean
            Get
                Return Me.elementBracingRightFrontFieldSpecified
            End Get
            Set
                Me.elementBracingRightFrontFieldSpecified = Value
            End Set
        End Property

        <System.Xml.Serialization.XmlAttributeAttribute()>
        Public Property ElementBracingRightRear() As Boolean
            Get
                Return Me.elementBracingRightRearField
            End Get
            Set
                Me.elementBracingRightRearField = Value
            End Set
        End Property

        <System.Xml.Serialization.XmlIgnoreAttribute()>
        Public Property ElementBracingRightRearSpecified() As Boolean
            Get
                Return Me.elementBracingRightRearFieldSpecified
            End Get
            Set
                Me.elementBracingRightRearFieldSpecified = Value
            End Set
        End Property

        <System.Xml.Serialization.XmlAttributeAttribute(DataType:="integer")>
        Public Property ElementWidth() As String
            Get
                Return Me.elementWidthField
            End Get
            Set
                Me.elementWidthField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class ModuleType
        Inherits EntityBase(Of ModuleType)

        Private elementsField As List(Of FModuleElement)

        Private filtersField As List(Of FilterType)

        Private internalHardwareField As ModuleTypeInternalHardware

        Private preFilterClampField As List(Of MiscSystemType)

        Private intermediateFilterClampField As List(Of MiscSystemType)

        Private guardFilterClampField As List(Of MiscSystemType)

        Private liftingLugsField As List(Of MiscSystemType)

        Private laddersField As List(Of MiscSystemType)

        Private safetyGatesField As List(Of MiscSystemType)

        Private moduleNumFiltersHighField As String

        Private moduleNumFiltersWideField As String

        Private includesVerticalSplitField As Boolean

        Private includesHorizontalSplitField As Boolean

        Private drainPanRequiredField As Boolean

        Private isUpperModuleField As Boolean

        Private isLowerModuleField As Boolean

        Public Sub New()
            MyBase.New
            Me.safetyGatesField = New List(Of MiscSystemType)
            Me.laddersField = New List(Of MiscSystemType)
            Me.liftingLugsField = New List(Of MiscSystemType)
            Me.guardFilterClampField = New List(Of MiscSystemType)
            Me.intermediateFilterClampField = New List(Of MiscSystemType)
            Me.preFilterClampField = New List(Of MiscSystemType)
            Me.internalHardwareField = New ModuleTypeInternalHardware
            Me.filtersField = New List(Of FilterType)
            Me.elementsField = New List(Of FModuleElement)
            Me.moduleNumFiltersHighField = "4"
            Me.moduleNumFiltersWideField = "7"
            Me.includesVerticalSplitField = False
            Me.includesHorizontalSplitField = False
            Me.drainPanRequiredField = False
            Me.isUpperModuleField = False
            Me.isLowerModuleField = False
        End Sub

        <System.Xml.Serialization.XmlArrayItemAttribute("Element", IsNullable:=False)>
        Public Property Elements() As List(Of FModuleElement)
            Get
                Return Me.elementsField
            End Get
            Set
                Me.elementsField = Value
            End Set
        End Property

        <System.Xml.Serialization.XmlArrayItemAttribute("Filter", IsNullable:=False)>
        Public Property Filters() As List(Of FilterType)
            Get
                Return Me.filtersField
            End Get
            Set
                Me.filtersField = Value
            End Set
        End Property

        Public Property InternalHardware() As ModuleTypeInternalHardware
            Get
                Return Me.internalHardwareField
            End Get
            Set
                Me.internalHardwareField = Value
            End Set
        End Property

        <System.Xml.Serialization.XmlElementAttribute("PreFilterClamp")>
        Public Property PreFilterClamp() As List(Of MiscSystemType)
            Get
                Return Me.preFilterClampField
            End Get
            Set
                Me.preFilterClampField = Value
            End Set
        End Property

        <System.Xml.Serialization.XmlElementAttribute("IntermediateFilterClamp")>
        Public Property IntermediateFilterClamp() As List(Of MiscSystemType)
            Get
                Return Me.intermediateFilterClampField
            End Get
            Set
                Me.intermediateFilterClampField = Value
            End Set
        End Property

        <System.Xml.Serialization.XmlElementAttribute("GuardFilterClamp")>
        Public Property GuardFilterClamp() As List(Of MiscSystemType)
            Get
                Return Me.guardFilterClampField
            End Get
            Set
                Me.guardFilterClampField = Value
            End Set
        End Property

        <System.Xml.Serialization.XmlElementAttribute("LiftingLugs")>
        Public Property LiftingLugs() As List(Of MiscSystemType)
            Get
                Return Me.liftingLugsField
            End Get
            Set
                Me.liftingLugsField = Value
            End Set
        End Property

        <System.Xml.Serialization.XmlElementAttribute("Ladders")>
        Public Property Ladders() As List(Of MiscSystemType)
            Get
                Return Me.laddersField
            End Get
            Set
                Me.laddersField = Value
            End Set
        End Property

        <System.Xml.Serialization.XmlElementAttribute("SafetyGates")>
        Public Property SafetyGates() As List(Of MiscSystemType)
            Get
                Return Me.safetyGatesField
            End Get
            Set
                Me.safetyGatesField = Value
            End Set
        End Property

        <System.Xml.Serialization.XmlAttributeAttribute(DataType:="integer"),
         System.ComponentModel.DefaultValueAttribute("4")>
        Public Property ModuleNumFiltersHigh() As String
            Get
                Return Me.moduleNumFiltersHighField
            End Get
            Set
                Me.moduleNumFiltersHighField = Value
            End Set
        End Property

        <System.Xml.Serialization.XmlAttributeAttribute(DataType:="integer"),
         System.ComponentModel.DefaultValueAttribute("7")>
        Public Property ModuleNumFiltersWide() As String
            Get
                Return Me.moduleNumFiltersWideField
            End Get
            Set
                Me.moduleNumFiltersWideField = Value
            End Set
        End Property

        <System.Xml.Serialization.XmlAttributeAttribute(),
         System.ComponentModel.DefaultValueAttribute(False)>
        Public Property IncludesVerticalSplit() As Boolean
            Get
                Return Me.includesVerticalSplitField
            End Get
            Set
                Me.includesVerticalSplitField = Value
            End Set
        End Property

        <System.Xml.Serialization.XmlAttributeAttribute(),
         System.ComponentModel.DefaultValueAttribute(False)>
        Public Property IncludesHorizontalSplit() As Boolean
            Get
                Return Me.includesHorizontalSplitField
            End Get
            Set
                Me.includesHorizontalSplitField = Value
            End Set
        End Property

        <System.Xml.Serialization.XmlAttributeAttribute(),
         System.ComponentModel.DefaultValueAttribute(False)>
        Public Property DrainPanRequired() As Boolean
            Get
                Return Me.drainPanRequiredField
            End Get
            Set
                Me.drainPanRequiredField = Value
            End Set
        End Property

        <System.Xml.Serialization.XmlAttributeAttribute(),
         System.ComponentModel.DefaultValueAttribute(False)>
        Public Property IsUpperModule() As Boolean
            Get
                Return Me.isUpperModuleField
            End Get
            Set
                Me.isUpperModuleField = Value
            End Set
        End Property

        <System.Xml.Serialization.XmlAttributeAttribute(),
         System.ComponentModel.DefaultValueAttribute(False)>
        Public Property IsLowerModule() As Boolean
            Get
                Return Me.isLowerModuleField
            End Get
            Set
                Me.isLowerModuleField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute(AnonymousType:=True, [Namespace]:="http://tempuri.org/Modules.xsd")>
    Partial Public Class ModuleTypeInternalHardware
        Inherits EntityBase(Of ModuleTypeInternalHardware)

        Private gratingField As List(Of MiscSystemType)

        Private dripPanField As List(Of MiscSystemType)

        Private gasketField As List(Of MiscSystemType)

        '''<summary>
        '''ModuleTypeInternalHardware class constructor
        '''</summary>
        Public Sub New()
            MyBase.New
            Me.gasketField = New List(Of MiscSystemType)
            Me.dripPanField = New List(Of MiscSystemType)
            Me.gratingField = New List(Of MiscSystemType)
        End Sub

        <System.Xml.Serialization.XmlElementAttribute("Grating")>
        Public Property Grating() As List(Of MiscSystemType)
            Get
                Return Me.gratingField
            End Get
            Set
                Me.gratingField = Value
            End Set
        End Property

        <System.Xml.Serialization.XmlElementAttribute("DripPan")>
        Public Property DripPan() As List(Of MiscSystemType)
            Get
                Return Me.dripPanField
            End Get
            Set
                Me.dripPanField = Value
            End Set
        End Property

        <System.Xml.Serialization.XmlElementAttribute("Gasket")>
        Public Property Gasket() As List(Of MiscSystemType)
            Get
                Return Me.gasketField
            End Get
            Set
                Me.gasketField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class MiscSystemType
        Inherits EntityBase(Of MiscSystemType)

        Private systemTypeField As String

        Private systemVersionField As String

        Private textField As List(Of String)

        '''<summary>
        '''MiscSystemType class constructor
        '''</summary>
        Public Sub New()
            MyBase.New
            Me.textField = New List(Of String)
        End Sub

        <System.Xml.Serialization.XmlAttributeAttribute()>
        Public Property SystemType() As String
            Get
                Return Me.systemTypeField
            End Get
            Set
                Me.systemTypeField = Value
            End Set
        End Property

        <System.Xml.Serialization.XmlAttributeAttribute()>
        Public Property SystemVersion() As String
            Get
                Return Me.systemVersionField
            End Get
            Set
                Me.systemVersionField = Value
            End Set
        End Property

        <System.Xml.Serialization.XmlTextAttribute()>
        Public Property Text() As List(Of String)
            Get
                Return Me.textField
            End Get
            Set
                Me.textField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute([Namespace]:="http://tempuri.org/Modules.xsd"),
     System.Xml.Serialization.XmlRootAttribute([Namespace]:="http://tempuri.org/Modules.xsd", IsNullable:=True)>
    Partial Public Class DoorHandleType
        Inherits EntityBase(Of DoorHandleType)

        Private includesLockField As Boolean

        Public Sub New()
            MyBase.New
            Me.includesLockField = True
        End Sub

        <System.Xml.Serialization.XmlAttributeAttribute(),
         System.ComponentModel.DefaultValueAttribute(True)>
        Public Property IncludesLock() As Boolean
            Get
                Return Me.includesLockField
            End Get
            Set
                Me.includesLockField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute(AnonymousType:=True, [Namespace]:="http://tempuri.org/Modules.xsd")>
    Partial Public Class FilterHouseDoorTypeHandles
        Inherits EntityBase(Of FilterHouseDoorTypeHandles)

        Private doorHandleInnerField As DoorHandleType

        Private doorHandleOuterField As DoorHandleType

        '''<summary>
        '''FilterHouseDoorTypeHandles class constructor
        '''</summary>
        Public Sub New()
            MyBase.New
            Me.doorHandleOuterField = New DoorHandleType
            Me.doorHandleInnerField = New DoorHandleType
        End Sub

        Public Property DoorHandleInner() As DoorHandleType
            Get
                Return Me.doorHandleInnerField
            End Get
            Set
                Me.doorHandleInnerField = Value
            End Set
        End Property

        Public Property DoorHandleOuter() As DoorHandleType
            Get
                Return Me.doorHandleOuterField
            End Get
            Set
                Me.doorHandleOuterField = Value
            End Set
        End Property
    End Class

    <System.CodeDom.Compiler.GeneratedCodeAttribute("Xsd2Code", "3.4.0.32990"),
     System.SerializableAttribute(),
     System.ComponentModel.DesignerCategoryAttribute("code"),
     System.Xml.Serialization.XmlTypeAttribute(AnonymousType:=True, [Namespace]:="http://tempuri.org/Modules.xsd")>
    Partial Public Class FilterHouseDoorTypeCorrosionCoupons
        Inherits EntityBase(Of FilterHouseDoorTypeCorrosionCoupons)

        Private couponSystemField As MiscSystemType

        '''<summary>
        '''FilterHouseDoorTypeCorrosionCoupons class constructor
        '''</summary>
        Public Sub New()
            MyBase.New
            Me.couponSystemField = New MiscSystemType
        End Sub

        Public Property CouponSystem() As MiscSystemType
            Get
                Return Me.couponSystemField
            End Get
            Set
                Me.couponSystemField = Value
            End Set
        End Property
    End Class
	
End Class
#End Region
