AddReference "Autodesk.Connectivity.WebServices"
AddReference "Autodesk.DataManagement.Client.Framework.Forms"
AddReference "Autodesk.DataManagement.Client.Framework.Vault"
AddReference "Autodesk.DataManagement.Client.Framework.Vault.Forms"

Imports System.Linq
Imports ACW = Autodesk.Connectivity.WebServices
Imports VDF = Autodesk.DataManagement.Client.Framework
Imports Autodesk.DataManagement.Client.Framework.Vault.Services
Imports Autodesk.DataManagement.Client.Framework.Vault.Currency.Connections
Imports Autodesk.DataManagement.Client.Framework.Vault.Currency.Properties

Sub Main()
	If TypeOf ThisDoc.Document Is AssemblyDocument Then 
		Dim assydoc As AssemblyDocument = ThisDoc.Document
		Call CheckVaultStatusFromAssembly(assydoc)
	Else
		'tough luck!
	End If
End Sub

Sub CheckVaultStatusFromAssembly(ByVal assyDoc As AssemblyDocument)
	For Each doc As Document In assyDoc.AllReferencedDocuments
		If TypeOf doc Is PartDocument Then
			If CheckVaultStatus(doc.FullFileName)= VaultStatus.kRefresh Then
				RefreshVaultStatusFromInventorBrowser(doc.FullFileName)
			End If
		Else
			If CheckVaultStatus(doc.FullFileName)= VaultStatus.kRefresh Then
				RefreshVaultStatusFromInventorBrowser(doc.FullFileName)
			End If
			Dim referencedAssembly As AssemblyDocument = doc
			CheckVaultStatusFromAssembly(referencedAssembly)
		End If
	Next
End Sub

Function CheckVaultStatus(ByVal filename As String) As VaultStatus
	filename = IO.Path.GetFileName(filename)
	Dim Connection As VDF.Vault.Currency.Connections.Connection = Nothing
	Dim results As VDF.Vault.Results.LogInResult = VDF.Vault.Library.ConnectionManager.LogIn("localhost", "Vault", "", "", AuthenticationFlags.WindowsAuthentication, Nothing)
    Connection = results.Connection
	
	Dim props As PropertyDefinitionDictionary = Connection.PropertyManager.GetPropertyDefinitions(VDF.Vault.Currency.Entities.EntityClassIds.Files, Nothing, PropertyDefinitionFilter.IncludeAll)
	Dim statusProp As PropertyDefinition = props.Item(PropertyDefinitionIds.Client.VaultStatus)
	
	Dim FileIter As VDF.Vault.Currency.Entities.FileIteration = Nothing
	Dim oFile As ACW.File = Nothing

	oFile = FindVaultFileByFileName(Connection, filename)
	If oFile IsNot Nothing Then
		FileIter = New VDF.Vault.Currency.Entities.FileIteration(Connection, oFile)
	End If
	
	Dim status As EntityStatusImageInfo = Connection.PropertyManager.GetPropertyValue(FileIter, statusProp, Nothing)
	Logger.Debug("Filename: " & filename & "Vault Status= " & status.Status.ToString())
	If status.Status.ToString() = "NotCheckedOut-Unknown-NotLatestConsumable-MatchesOlderVaultVersion-MatchesLatestRevision-DoesNotHaveLocalEdits-None" Then
		Return VaultStatus.kRefresh
	Else
		Return VaultStatus.kIgnore	
	End If
End Function

Private Function FindVaultFileByFileName(Connection As VDF.Vault.Currency.Connections.Connection, filename As String) As ACW.File

    Dim result As ACW.File = Nothing

    Dim filePropDefs As ACW.PropDef() = Connection.WebServiceManager.PropertyService.GetPropertyDefinitionsByEntityClassId("FILE")
    Dim fileNamePropDef As ACW.PropDef = filePropDefs.[Single](Function(n) n.SysName = "ClientFileName")
    Dim fileNameMatch As New ACW.SrchCond()

	fileNameMatch.PropDefId = fileNamePropDef.Id
    fileNameMatch.PropTyp = ACW.PropertySearchType.SingleProperty
    fileNameMatch.SrchOper = 3
    fileNameMatch.SrchRule = ACW.SearchRuleType.Must
    fileNameMatch.SrchTxt = filename

    Dim bookmark As String = String.Empty
    Dim searchStatus As ACW.SrchStatus = Nothing
    Dim searchResults As ACW.File() = Connection.WebServiceManager.DocumentService.FindFilesBySearchConditions(New ACW.SrchCond() {fileNameMatch}, Nothing, Nothing, False, True, bookmark, searchStatus)

    If searchResults IsNot Nothing Then
        If searchResults.Length > 0 Then
           result = searchResults(0)
        End If
    End If

    Return result

End Function

Sub RefreshVaultStatusFromInventorBrowser(ByVal filename As String)
	For Each Pane As BrowserPane In ThisApplication.ActiveDocument.BrowserPanes
		Logger.Debug("Internal Name: " & Pane.InternalName & vbCrLf & "Display Name: " & Pane.Name)
        If Pane.InternalName = "AmBrowserArrangement" Then
            For i = 1 To Pane.TopNode.BrowserNodes.Count
				Dim node As BrowserNode = Pane.TopNode.BrowserNodes.Item(i)
				Logger.Debug("node.FullPath: " & node.FullPath)
                If Not node.NativeObject Is Nothing Then
					Logger.Debug("Node Type Name: " & TypeName(node))
					Logger.Debug("Node NativeObject Type Name: " & TypeName(node.NativeObject))
					If TypeOf node.NativeObject Is ComponentOccurrence Then
						Dim thisOcc As ComponentOccurrence = node.NativeObject
						Dim thisDoc As Document = thisOcc.Definition.Document
						If thisDoc.FullFileName.Contains(filename) Then
							ThisApplication.ActiveDocument.selectset.clear()
							ThisApplication.ActiveDocument.selectset.select(thisOcc)
							Call RefreshVaultStatus()
						End If
                    End If
                End If
            Next
        End If
    Next
End Sub

Sub RefreshVaultStatus()
	If ThisApplication.ActiveDocument.selectset.count > 0 Then
		Dim refreshCmd As ControlDefinition = ThisApplication.CommandManager.ControlDefinitions("RefreshRevision")
		refreshCmd.Execute()
	End If
End Sub

Public Enum VaultStatus
	kRefresh
	kIgnore
	kOutOfDate
End Enum
