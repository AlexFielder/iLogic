Imports Inventor
Imports System.Reflection
Imports System
Sub Main()
	GetProperties(ThisApplication.ActiveDocument)
End Sub

Sub GetProperties(myObject As Object)
	Dim propstr As String = String.Empty
	Try
		Dim myType As Type = myObject.[GetType]()
		Dim props As IList(Of PropertyInfo) = Nothing
		Dim typename As String = Microsoft.VisualBasic.Information.TypeName(myObject)
		If typename = "AssemblyDocument" Then
			Dim assyDoc As AssemblyDocument = TryCast(myType, AssemblyDocument)
			props = GetType(AssemblyDocument).GetProperties().ToList()
		Else If typename = "PartDocument" Then
			Dim partDoc As PartDocument = TryCast(myType, PartDocument)
			props = GetType(PartDocument).GetProperties().ToList()
		Else
			Exit Sub
		End If
		
		MessageBox.Show(props.Count)
		For Each prop As PropertyInfo In props
			If Not prop.Name = Nothing Then
				MessageBox.Show(prop.Name)
			Else
				MessageBox.Show(prop.ToString())
			End If
			Dim propValue As Object = prop.GetValue(myObject, Nothing)
			If Not propValue Is Nothing Then
				If propstr = String.Empty Then
					propstr = propValue.ToString()
				Else
					propstr = propstr & vbCrLf & propValue.ToString()
				End If
			End If
		Next
	Catch ex As Exception
		MessageBox.Show("Exception was: " & ex.Message & ex.StackTrace)
	Finally
		MessageBox.Show("Resultant properties of myobject: " & myObject.ToString() & " were: " & propstr)
	End Try
End Sub

'Sub GetProperties(myObject As Object)
'	MessageBox.Show(myObject.DocumentType)
'	Dim typename As String = Microsoft.VisualBasic.Information.TypeName(myObject)
'	MessageBox.Show(typename)
'	Dim myType As Type = Type.GetType(typename, True)
'	'Dim currentNamespace As String = Type.GetType(typename, True).Namespace
'	'MessageBox.Show(currentNamespace & " " & typename)
'	If Not myType = Nothing Then
'		Dim props As IList(Of PropertyInfo) = New List(Of PropertyInfo)(myType.GetProperties())
'		Dim propstr As String = String.Empty
'		MessageBox.Show(props.Count)
'		For Each prop As PropertyInfo In props
'			Dim propValue As Object = prop.GetValue(myObject, Nothing)
'			If propstr = String.Empty Then
'				propstr = propValue.ToString()
'			Else
'				propstr = propstr & vbCrLf & propValue.ToString()
'			End If
'		Next
'		MessageBox.Show("Resultant properties of myobject: " & myObject.ToString() & " were: " & propstr)
'	Else
'		Messagebox.Show("we broke it.")
'	End If
'End Sub

'Private Sub SurroundingSub()
'    Dim prop As System.Reflection.PropertyInfo = GetType(PartDocument).GetProperty("FullFilename")
'    query = query.OrderBy(Function(x) prop.GetValue(x, Nothing))
'End Sub

' not sure this will work: ?
'Private Sub SurroundingSub()
'    typeName = Microsoft.VisualBasic.Information.TypeName(someCOMObject)

'    For Each assembly As System.Reflection.Assembly In AppDomain.CurrentDomain.GetAssemblies()

'        For Each type As Type In assembly.GetTypes()
'            If (TryCast(someCOMObject, type)) IsNot Nothing Then fullTypeName = type.FullName
'        Next
'    Next
'End Sub
