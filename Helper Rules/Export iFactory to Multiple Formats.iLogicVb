Sub Main()
ExportiFactoryToMultiple()
End Sub

'A COUPLE OF GLOBAL VARIABLES
Public CurrentPath As String = ""
Public NewPath As String = ""

Sub ExportiFactoryToMultiple(Optional ByVal formatInt As Integer = 0)
    Dim oErrorManager As ErrorManager = ThisApplication.ErrorManager
	CurrentPath = System.IO.Path.getdirectoryname(ThisApplication.activedocument.fulldocumentname)
	NewPath = CurrentPath & "\"& System.IO.Path.GetFileNameWithoutExtension(ThisApplication.activedocument.fulldocumentname) & "\"
    If TypeOf (ThisApplication.activedocument) Is partdocument Then
	
        Dim oDoc As PartDocument = ThisApplication.ActiveDocument
        Dim oiPart As iPartFactory = oDoc.ComponentDefinition.iPartFactory
        Dim oTop As BrowserNode = oDoc.BrowserPanes("Model").TopNode
        Dim bHasErrorOrWarning As Boolean
        Dim i As Integer
        InventorVb.DocumentUpdate()
        ThisApplication.SilentOperation = True
        For i = 1 To oiPart.TableRows.Count 'use first 10 rows only for debugging purposes!
            ' Highlight the 3rd iPart table row which has invalid data
            oTop.BrowserNodes("Table").BrowserNodes.Item(i).DoSelect

            ' Activate the iPart table row
            Dim oCommand As ControlDefinition = ThisApplication.CommandManager.ControlDefinitions("PartComputeiPartRowCtxCmd")
            oCommand.Execute

            ThisApplication.SilentOperation = False
            ThisApplication.CommandManager.ControlDefinitions.Item("AppZoomallCmd").Execute
			ExportToStep(oiPart.TableRows.Item(i).MemberName)
			'ExportDXF(oiPart.TableRows.Item(i).MemberName)
            If oErrorManager.HasErrors Or oErrorManager.HasWarnings Then
                MessageBox.Show(oErrorManager.LastMessage, "Title")
            End If
        Next i
        MessageBox.Show("No errors shown = None found!", "Title")
    ElseIf TypeOf (ThisApplication.activedocument) Is assemblydocument Then
        Dim odoc As assemblydocument = ThisApplication.activedocument
        Dim iAssy As iAssemblyFactory = odoc.componentdefinition.iassemblyfactory
        Dim oTop As BrowserNode = odoc.BrowserPanes("Model").TopNode
        Dim bHasErrorOrWarning As Boolean
        Dim i As Integer
        InventorVb.DocumentUpdate()
        ThisApplication.SilentOperation = True
        For rowIndex = 1 To iAssy.tablerows.count
            oTop.BrowserNodes("Table").BrowserNodes.Item(i).DoSelect
            Dim oCommand As ControlDefinition = ThisApplication.CommandManager.ControlDefinitions("PartComputeiPartRowCtxCmd")
            oCommand.Execute
            ThisApplication.SilentOperation = False
            ThisApplication.CommandManager.ControlDefinitions.Item("AppZoomallCmd").Execute
			ExportToStep(iassy.TableRows.Item(i).MemberName)
			ExportDXF(iassy.TableRows.Item(i).MemberName)
            If oErrorManager.HasErrors Or oErrorManager.HasWarnings Then
                MessageBox.Show(oErrorManager.LastMessage, "Title")
            End If

        Next
    End If
End Sub

Private Sub ExportToStep(LastActiveFeatureName As String)
	' Get the STEP translator Add-In.
	Dim oSTEPTranslator As TranslatorAddIn
	oSTEPTranslator = ThisApplication.ApplicationAddIns.ItemById("{90AF7F40-0C01-11D5-8E83-0010B541CD80}")
	Dim oContext As TranslationContext
	oContext = ThisApplication.TransientObjects.CreateTranslationContext
	Dim oOptions As NameValueMap
	oOptions = ThisApplication.TransientObjects.CreateNameValueMap

	If oSTEPTranslator.HasSaveCopyAsOptions(ThisApplication.ActiveDocument, oContext, oOptions) Then
		' Set application protocol.
		' 2 = AP 203 - Configuration Controlled Design
		' 3 = AP 214 - Automotive Design
		oOptions.Value("ApplicationProtocolType") = 3
		' Other options...
		'oOptions.Value("Author") = ""
		'oOptions.Value("Authorization") = ""
		'oOptions.Value("Description") = ""
		'oOptions.Value("Organization") = ""
		oContext.Type = IOMechanismEnum.kFileBrowseIOMechanism
		Dim oData As DataMedium
		oData = ThisApplication.TransientObjects.CreateDataMedium
		oData.FileName = NewPath & LastActiveFeatureName & ".stp"
		'oData.FileName = ThisDoc.PathAndFileName(False) & "_" & LastActiveFeatureName & "-exported.stp"
		oSTEPTranslator.SaveCopyAs(ThisApplication.ActiveDocument, oContext, oOptions, oData)
		'OpenAndSaveExportedStep(oData.FileName)
	End If
End Sub

'copied from https://forums.autodesk.com/t5/inventor-customization/ilogic-rule-to-ask-yes-or-no-for-dxf-export-when-saving-idw/td-p/3939068
Public Sub 	ExportDXF(ByVal outputfilename As String)
	' Get the DXF translator Add-In.
	'path_and_nameDXF = ThisDoc.PathAndFileName(False)
	Dim DXFAddIn As TranslatorAddIn
	DXFAddIn = ThisApplication.ApplicationAddIns.ItemById("{C24E3AC4-122E-11D5-8E91-0010B541CD80}")
	'Set a reference to the active document (the document to be published).
	Dim oDocument As Document
	oDocument = ThisApplication.ActiveDocument
	Dim oContext As TranslationContext
	oContext = ThisApplication.TransientObjects.CreateTranslationContext
	oContext.Type = IOMechanismEnum.kFileBrowseIOMechanism
	' Create a NameValueMap object
	Dim oOptions As NameValueMap
	oOptions = ThisApplication.TransientObjects.CreateNameValueMap
	' Create a DataMedium object
	Dim oDataMedium As DataMedium
	oDataMedium = ThisApplication.TransientObjects.CreateDataMedium
	'If DXFAddIn.HasSaveCopyAsOptions(oDocument, oContext, oOptions) Then
	'	Dim strIniFile As String
	'	strIniFile = "C:\Users\Farr\Documents\Inventor\DXF_EXPORT_INI\DXF_EXPORT.ini"
	'	oOptions.Value("Export_Acad_IniFile") = strIniFile
	'End If
	oDataMedium.FileName = NewPath & outputfilename & ".dxf"
	Call DXFAddIn.SaveCopyAs(oDocument, oContext, oOptions, oDataMedium)
End Sub
