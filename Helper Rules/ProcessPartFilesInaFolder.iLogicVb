AddReference "System.Core"
AddReference "System.Linq"
'addreference "Microsoft.Win32"

Imports Inventor
Imports System.IO
Imports System.Core
Imports System.Linq
Imports System.Windows.Forms
Imports System.Collections.Generic
Imports Microsoft.Win32

''' <summary>
''' 
''' </summary>
Public Sub Main()
    'user feedback tools start
    Dim sw As New Stopwatch()
    sw.Start()

    Dim IncludeSubFolders As Boolean = True


    ProcessPartsinFolder(IncludeSubFolders)
    sw.Stop()
    Dim timeElapsed As Timespan = sw.elapsed
    MessageBox.Show("Processing took: " & String.Format("{0:00}:{1:00}:{2:00}.{3:00}",
                                                        timeElapsed.Hours,
                                                        timeElapsed.Minutes,
                                                        timeElapsed.Seconds,
                                                        timeElapsed.Milliseconds / 10))

End Sub

''' <summary>
''' Prompts the user to select a folder then processes the part files contained within
''' </summary>
''' <param name="includeSubfolders"></param>
Public Sub ProcessPartsinFolder(ByVal includeSubfolders As Boolean)
	'default folder
	Dim oDesignProjectMgr As DesignProjectManager = ThisApplication.DesignProjectManager
	Dim oProject As DesignProject = oDesignProjectMgr.DesignProjects.ItemByName(oDesignProjectMgr.ActiveDesignProject.FullFileName)
	Dim FolderName As String = oProject.WorkspacePath()
    Dim iLogicAuto As Object = GetiLogicAutomation(ThisApplication)
    Dim folderbrowser As New System.Windows.Forms.FolderBrowserDialog()
	folderbrowser.SelectedPath = FolderName
'	folderbrowser.RootFolder = FolderName
    'folderbrowser.RootFolder = System.Environment.SpecialFolder.MyComputer
	'folderbrowser.RootFolder = System.Environment.SpecialFolder.UserProfile
    'folderbrowser.RootFolder = getOneDriveFolderPath()
    folderbrowser.Description = "Select Folder to look for files to process."
    folderbrowser.ShowDialog()
    foldername = folderbrowser.selectedpath
    If Not foldername = String.Empty Then
        'now we can get/create a list of part files
		Dim Rulesfolderbrowser As New System.Windows.Forms.FolderBrowserDialog()
    	Rulesfolderbrowser.RootFolder = System.Environment.SpecialFolder.MyComputer
		Rulesfolderbrowser.Description = "Select your external iLogic rules folder:"
		Rulesfolderbrowser.SelectedPath = getDropBoxFolderPath() & "\iLogic\"
		Logger.Debug(Rulesfolderbrowser.SelectedPath)
		Rulesfolderbrowser.ShowDialog()
		Dim externalRulesFolder As String = rulesFolderBrowser.selectedpath
		If Not externalRulesFolder = String.Empty Then
			Dim rulename As String = SelectRuleToProcessPartsWith(externalRulesFolder)
			'Dim rulename As String = SelectRuleToProcessPartsWith(getDropBoxFolderPath() & "\iLogic\")
			If Not rulename = String.Empty Then
				Logger.Debug("Running: " & rulename)
				Dim directory As New System.IO.DirectoryInfo(FolderName)
				Dim partlisttoprocess As List(Of FileInfo) = GetFilesByExtensions(directory, ".ipt").ToList()
'				Dim partlisttoprocess As System.Collections.Generic.IEnumerable(Of fileinfo) = GetFilesByExtensions(directory, ".ipt")
				Logger.Debug("Number of part files to process: "& partlisttoprocess.Count)
				Dim progressint As Integer = 1
				Dim percent As Double = Nothing
	
				If Not partlisttoprocess Is Nothing Then
					For Each partfile As fileinfo In partlisttoprocess
	
						percent = (CDbl(progressint) / partlisttoprocess.Count)
						progressint += 1
	
						Dim partdoc As partdocument = ThisApplication.documents.Open(partfile.fullname)
	
						updatestatusbar(percent, "Processing: " & System.IO.Path.GetFileNameWithoutExtension(partdoc.File.fullfilename))
						'insert the name of the external rule you wish to run here:
						'iLogicAuto.RunExternalRule(partdocument, rulename)
						Dim Args As NameValueMap = ThisApplication.transientobjects.createnamevaluemap
						Args.Value("Filename") = partdoc.FullFileName
						Logger.Debug("processing: " & partdoc.FullFileName)
						iLogicAuto.RunExternalRuleWithArguments(partdoc, rulename, Args)
						partdoc.Close()
					Next
				End If
			Else
				MessageBox.Show("You didn't select your external iLogic rules folder!")
			End If
		Else
			MessageBox.Show("You didn't select your external iLogic rules folder!")
		End If
	Else
		MessageBox.Show("You didn't select a folder to process!")
    End If
End Sub

'Public Function GetListofExternaliLogicFolders() As String()
'    'the following might work one day, but 2016-09-13 is not that day.
'    Dim iLogicInterfaces As Object = GetiLogicInterfaces(ThisApplication)
'    Return iLogicInterfaces.iLogicFileOptions.ExternalRuleDirectories
'End Function

''' <summary>
''' 
''' </summary>
''' <param name="InventorExternalRulesFolderPath"></param>
''' <returns></returns>
Public Function SelectRuleToProcessPartsWith(ByVal InventorExternalRulesFolderPath As String) As String
    Dim partlisttoprocess As System.Collections.Generic.IEnumerable(Of fileinfo)
    'For Each foldername As String In InventorExternalRulesFolderPath
    Dim directory As New System.IO.DirectoryInfo(InventorExternalRulesFolderPath)
    partlisttoprocess = GetFilesByExtensions(directory, ".iLogicVb")
    'Next
    Dim RulesList As New ArrayList

    For Each file As System.IO.FileInfo In partlisttoprocess
        RulesList.add(System.IO.Path.GetFileNameWithoutExtension(file.FullName))
    Next
    Dim selectedfile As String = InputListBox("Prompt", RulesList, "", Title:="Select Rule from this list", ListName:="Available External Rules")


    Try
        'oFileDlg.ShowOpen()
        selectedfile = System.IO.Path.GetFileNameWithoutExtension(selectedfile)
    Catch
        Return Nothing 'operation was cancelled by the user
    End Try
    Return selectedfile
End Function

Public Function GetFilesByExtensions(ByVal dir As DirectoryInfo,ByVal ParamArray extensions As String()) As System.Collections.Generic.IEnumerable(Of FileInfo)
	break
	Logger.Debug("Path: " & dir.fullname)
    If extensions Is Nothing Then
        Throw New ArgumentNullException("extensions")
    End If
    Dim files As System.Collections.Generic.IEnumerable(Of FileInfo) = dir.EnumerateFiles("*.*", SearchOption.AllDirectories).Where(Function(s As FileInfo) Not (s.FullName.contains("OldVersions")))
    'Dim files = dir.EnumerateFiles("*.*", SearchOption.AllDirectories).Where(Function(s As FileInfo) Not (s.FullName.Contains("-")) OrElse Not (s.FullName.contains("OldVersions")))
    'Return files
	Logger.Debug(files.ToList().Count())
    Return files.Where(Function(f As FileInfo) extensions.Contains(f.Extension)).Orderby(Function(x As FileInfo) x.Name)
End Function

Sub updatestatusbar(ByVal message As String)
    ThisApplication.statusbartext = message
End Sub

Sub updatestatusbar(ByVal percent As Double, ByVal message As String)
    ThisApplication.statusbartext = message + " (" & percent.ToString("P1") + ")"
End Sub

''' <summary>
''' Gets the iLogic Automation interface from the current Inventor application.
''' </summary>
''' <param name="app"></param>
''' <returns></returns>
Function GetiLogicAutomation(ByVal app As Inventor.Application) As Object

    Dim addIn As Inventor.ApplicationAddIn = Nothing
    Try
        addIn = app.ApplicationAddIns.ItemById("{3bdd8d79-2179-4b11-8a5a-257b1c0263ac}")
    Catch ex As Exception
        Return Nothing
    End Try

    Return addIn.Automation
End Function

Private Function getOneDriveFolderPath() As String
    Dim value1 = Registry.GetValue("HKEY_CURRENT_USER\Software\Microsoft\SkyDrive", "UserFolder", Nothing)
    Dim path1 = TryCast(value1, String)
    If path1 IsNot Nothing AndAlso System.IO.Directory.Exists(path1) Then Return path1
    Dim value2 = Registry.GetValue("HKEY_CURRENT_USER\Software\Microsoft\Windows\CurrentVersion\SkyDrive", "UserFolder", Nothing)
    Dim path2 = TryCast(value2, String)
    If path2 IsNot Nothing AndAlso System.IO.Directory.Exists(path2) Then Return path2
    Dim value3 = Registry.GetValue("HKEY_CURRENT_USER\Software\Microsoft\OneDrive", "UserFolder", Nothing)
    Dim path3 = TryCast(value3, String)
    If path3 IsNot Nothing AndAlso System.IO.Directory.Exists(path3) Then Return path3
    Return Nothing
End Function

Private Function getDropBoxFolderPath() As String
	'break
    Dim infoPath = "Dropbox\info.json"
    'Dim Appdata As String = Environment.SpecialFolder.LocalApplicationData
    Dim jsonPath As String = System.IO.Path.Combine(System.Environment.GetFolderPath(System.Environment.SpecialFolder.LocalApplicationData), infoPath)
    'Dim jsonPath = Path.Combine(Environment.GetEnvironmentVariable("LocalAppData"), infoPath)
    'debug only
    'MessageBox.Show(jsonPath)
    If Not System.IO.File.Exists(jsonPath) Then
        jsonPath = System.IO.Path.Combine(System.Environment.GetFolderPath(System.Environment.SpecialFolder.ApplicationData), infoPath)
        'jsonPath = Path.Combine(Environment.GetEnvironmentVariable("AppData"), infoPath)
    End If
    'debug only
    'MessageBox.Show(jsonPath)

    If Not System.IO.File.Exists(jsonPath) Then
        Throw New Exception("Dropbox could not be found!")
    End If

    Dim dropboxPath = System.IO.File.ReadAllText(jsonPath).Split(""""c)(13).Replace("\\", "\")
	logger.debug("Dropbox path: " & dropboxPath)
    Return dropboxPath
End Function
