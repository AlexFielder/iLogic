Imports AII = Autodesk.iLogic.Interfaces
Sub main()
	Dim oObj As Object = ThisApplication.CommandManager.Pick(SelectionFilterEnum.kAllEntitiesFilter, "Select a Face, Edge or Vertex")
	If Not oObj Is Nothing Then
		namedEnts = ThisDoc.NamedEntities
		Dim geomInt As Integer = 1
		Dim newAttributeName As String = GetNewOrDefaultNameFromEntities(oObj, "", geomInt)
		
		newAttributeName = InputBox("What name For the Geometry?", "Naming Day", newAttributeName)
'Break
		newAttributeName = GetNewOrDefaultNameFromEntities(oObj, newAttributeName, geomInt)
		namedEnts.SetName(oObj, newAttributeName)
	End If
End Sub

Public namedEnts As AII.NamedEntities = Nothing

''' <summary>
''' Gets a default result which matches the manual approach.
''' </summary>
''' <param name="oobj"></param>
''' <param name="geomInt"></param>
''' <returns></returns>
Function GetDefaultResponseFromType(ByVal oobj As Object, ByVal geomInt As Integer) As String
	Dim defaultResponseFromType As String = String.Empty
	Select Case TypeName(oobj)
		Case "Vertex"
			defaultResponseFromType = TypeName(oobj) & geomInt.ToString("0")
		Case Else
			defaultResponseFromType = TypeName(oobj) & "Geom" & geomInt.ToString("000")
	End Select
	Return defaultResponseFromType
End Function

''' <summary>
''' Returns the expected name based on
''' </summary>
''' <param name="attrName"></param>
''' <param name="geomInt"></param>
''' <returns></returns>
Function GetNewOrDefaultNameFromEntities(ByVal oobj As Object, ByVal attrName As String, ByVal geomInt As Integer) As String
	If attrName = String.Empty 
		attrName = GetDefaultResponseFromType(oobj, geomInt)
	End If
	
	Do While namedEnts.NameExists(attrName)
		If Not namedEnts.NameExists(attrName) Then
			Return attrName
		Else
			geomInt += 1
			attrName = GetDefaultResponseFromType(oobj, geomInt)
			If Not namedEnts.NameExists(attrName) Then
				Return attrName
				Exit Do
			End If
		End If	
	Loop
	If Not namedEnts.NameExists(attrName) Then Return attrName
End Function
