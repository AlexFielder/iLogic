Option Explicit On
Imports System.IO

''' <summary>
''' Will only run if the activedocument has been saved.
''' </summary> 
Sub Main()
	Dim trans As Transaction = ThisApplication.TransactionManager.StartTransaction(ThisApplication.ActiveDocument, "Export and Attach Step file")
	Try
		If Not ThisApplication.ActiveDocument.FullFilename = String.Empty Then 'won't run if the active document isn't saved.
			Dim filenameToAttach As String = PrintDocument(ThisApplication.ActiveDocument)
			If Not filenameToAttach = String.Empty Then
				Dim doc As Document = ThisApplication.ActiveDocument
				AddReferences(doc, filenameToAttach)
			End If
		Else
			MessageBox.Show("File not saved; save the file and try again!")
			trans.Abort()
		End If
		trans.End()
	Catch
		trans.Abort()
	End Try
End Sub

''' <summary>
''' Prints the current document to pdf of the same filename in the same location as the drawing file.
''' </summary>
''' <param name="printDoc"></param>
''' <returns></returns>
Public Function PrintDocument(ByVal printDoc As DrawingDocument) As String
	Dim oPDFAddIn As ApplicationAddIn = ThisApplication.ApplicationAddIns.ItemById("{0AC6FD96-2F4D-42CE-8BE0-8AEA580399E4}")
	Dim oContext As TranslationContext = ThisApplication.TransientObjects.CreateTranslationContext
	oContext.Type = IOMechanismEnum.kFileBrowseIOMechanism
	Dim oOptions As NameValueMap = ThisApplication.TransientObjects.CreateNameValueMap
	Dim oDataMedium As DataMedium = ThisApplication.TransientObjects.CreateDataMedium
	If oPDFAddIn.HasSaveCopyAsOptions(printDoc, oContext, oOptions) Then
		oOptions.Value("All_Color_AS_Black") = 1
		oOptions.Value("Remove_Line_Weights") = 1
		oOptions.Value("Vector_Resolution") = 400
		oOptions.Value("Sheet_Range") = Inventor.PrintRangeEnum.kPrintAllSheets
	End If

	oDataMedium.FileName = System.IO.Path.GetFileNameWithoutExtension(printDoc.Fullfilename) & ".pdf"

	Try
		Call oPDFAddIn.SaveCopyAs(printDoc, oContext, oOptions, oDataMedium)
		ThisApplication.StatusBarText = "PDF SAVED TO: " & oDataMedium.FileName
	Catch
		MessageBox.Show("PDF could not be saved, most likely you or someone else has it open", "No PDF for you " & ThisApplication.GeneralOptions.UserName & "!")
	End Try
	If System.IO.File.Exists(oDataMedium.FileName) Then
		MessageBox.Show("Printed document path is: " & System.IO.Path.GetFileNameWithoutExtension(printDoc.Fullfilename) & ".pdf")
		Return System.IO.Path.GetFileNameWithoutExtension(printDoc.Fullfilename) & ".pdf" ' oDataMedium.FileName
	Else
		Return String.Empty
	End If
End Function

''' <summary>
''' Attaches any file using the fully c:\path\to\your\file.extension format.
''' </summary>
''' <param name="odoc"></param>
''' <param name="selectedfile"></param>
Public Sub AddReferences(ByVal odoc As Inventor.Document, ByVal selectedfile As String)
	Dim oleReference As ReferencedOLEFileDescriptor
	If selectedfile.Contains("|") Then ' we have multiple files selected.
		Dim file As String() = selectedfile.Split("|")
		For Each s As String In file
			oleReference = odoc.ReferencedOLEFileDescriptors _
				.Add(s, OLEDocumentTypeEnum.kOLEDocumentLinkObject)
			oleReference.BrowserVisible = True
			oleReference.Visible = False
			oleReference.DisplayName = Mid$(s, InStrRev(s, "\") + 1)
		Next
	Else
		oleReference = odoc.ReferencedOLEFileDescriptors _
				.Add(selectedfile,OLEDocumentTypeEnum.kOLEDocumentLinkObject)
		oleReference.BrowserVisible = True
		oleReference.Visible = False
		oleReference.DisplayName = Mid$(selectedfile, InStrRev(selectedfile, "\") + 1)
	End If
End Sub
