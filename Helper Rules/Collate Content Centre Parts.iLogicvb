AddReference "System.Core"
AddReference "System.Linq"
AddReference "System.IO"

Imports System.LINQ
Imports System.Collections.Generic
Imports System.IO
Imports System.Text
Imports System.Text.RegularExpressions

Public Sub Main()
	RunRenumberItems()
End Sub

Private Shared ccBomRowItems As List(Of BomRowItem) = Nothing

Private Shared ccPartsList As List(Of PartDocument) = Nothing

Private Shared itemisedPartsList As List(Of Document) = Nothing

'Private Shared ItemNo As Integer = 500

Private Sub RunRenumberItems()
    Try
		
		'should really check that we're running this in an assembly...
        Dim AssyDoc As AssemblyDocument = ThisApplication.ActiveDocument
		Dim OutputFileName As String  = System.IO.Path.GetDirectoryName(AssyDoc.FullFileName) + "\BomRowItems.txt"
		If (System.IO.File.Exists(OutputFileName))
			System.IO.File.Delete(OutputFileName)
		End If
		
		Using fs as FileStream = System.IO.File.Create(OutputFileName)
	'       itemisedPartsList =(From referencedItem In AssyDoc.AllReferencedDocuments Order By referencedItem.FullFileName Select referencedItem).ToList()
			itemisedPartsList = (From referencedItem as Document In AssyDoc.allreferenceddocuments Select referencedItem).ToList()
			AssySubAssemblies = itemisedPartsList.OfType(Of AssemblyDocument)().ToList()
			ccPartsList =(From ccDoc In AssyDoc.AllReferencedDocuments 
			Where ccDoc.FullFileName.Contains("Content Center") Or Not SetorCreateCustomiProperty(ccDoc, "ItemNo") = Nothing And SetorCreateCustomiProperty(ccDoc, "ItemNo").ToString().StartsWith("5")
			Let folderName = System.IO.Path.GetDirectoryName(ccDoc.FullFileName) 
			Let nonReferencePartDoc = CType(ccDoc, PartDocument) 
			Where nonReferencePartDoc.ComponentDefinition.BOMStructure <> BOMStructureEnum.kReferenceBOMStructure 
			Order By folderName 
			Select nonReferencePartDoc).Distinct().ToList()
			Dim tmpBomRowItems As List(Of BomRowItem) = New List(Of BomRowItem)()
			If ccPartsList IsNot Nothing Then
				If ccBomRowItems Is Nothing Then
					ccBomRowItems = New List(Of BomRowItem)()
					For Each doc As Document In ccPartsList
						'AddText(fs, ItemNo.ToString() + " - " + GetorSetStandardiProperty(doc, PropertiesForDesignTrackingPropertiesEnum.kMaterialDesignTrackingProperties, "", "") + " - " + doc.FullFileName + vbCrLf)
						AddText(fs, SetorCreateCustomiProperty(doc, "ItemNo").ToString() + " - " + GetorSetStandardiProperty(doc, PropertiesForDesignTrackingPropertiesEnum.kMaterialDesignTrackingProperties, "", "") + " - " + doc.FullFileName + vbCrLf)
						'Dim item As BomRowItem = New BomRowItem With {.ItemNo = ItemNo.ToString(), .Document = doc.FullFileName, .Material = GetorSetStandardiProperty(doc, PropertiesForDesignTrackingPropertiesEnum.kMaterialDesignTrackingProperties, "", ""), .Quantity = 1, .WhereUsed = New List(Of String)()}
						Dim item As BomRowItem = New BomRowItem With {.ItemNo = SetorCreateCustomiProperty(doc, "ItemNo").ToString(), .Document = doc.FullFileName, .Material = GetorSetStandardiProperty(doc, PropertiesForDesignTrackingPropertiesEnum.kMaterialDesignTrackingProperties, "", ""), .Quantity = 1, .WhereUsed = New List(Of String)()}
						ccBomRowItems.Add(item)
'						ItemNo += 1
					Next
				Else
'					ItemNo = Convert.ToInt32((From item In ccBomRowItems Order By item.ItemNo Select item.ItemNo).Last())
'					ItemNo += 1
					For Each doc As Document In ccPartsList
						Dim existingItem As BomRowItem =(From m In ccBomRowItems Where m.Document = doc.FullFileName Select m).FirstOrDefault()
						If existingItem Is Nothing Then
							'AddText(fs, ItemNo.ToString() + " - " + GetorSetStandardiProperty(doc, PropertiesForDesignTrackingPropertiesEnum.kMaterialDesignTrackingProperties, "", "") + " - " + doc.FullFileName + vbCrLf)
						AddText(fs, SetorCreateCustomiProperty(doc, "ItemNo").ToString() + " - " + GetorSetStandardiProperty(doc, PropertiesForDesignTrackingPropertiesEnum.kMaterialDesignTrackingProperties, "", "") + " - " + doc.FullFileName + vbCrLf)
							'Dim item As BomRowItem = New BomRowItem With {.ItemNo = ItemNo.ToString(), .Document = doc.FullFileName, .Material = GetorSetStandardiProperty(doc, PropertiesForDesignTrackingPropertiesEnum.kMaterialDesignTrackingProperties, "", ""), .Quantity = 1, .WhereUsed = New List(Of String)()}
							Dim item As BomRowItem = New BomRowItem With {.ItemNo = SetorCreateCustomiProperty(doc, "ItemNo").ToString(), .Document = doc.FullFileName, .Material = GetorSetStandardiProperty(doc, PropertiesForDesignTrackingPropertiesEnum.kMaterialDesignTrackingProperties, "", ""), .Quantity = 1, .WhereUsed = New List(Of String)()}
'							ItemNo += 1
						End If
					Next
				End If
	
	'            ConvertBomRowItemsToAttributes()
	            ProcessAllAssemblyOccurrences()
			End If
		End Using
    Catch ex As Exception
        MessageBox.Show(ex.Message & ex.stacktrace)
    End Try
End Sub

Sub AddText(fs as FileStream, value As String)
	Dim info As Byte() = New UTF8Encoding(True).GetBytes(value)
    fs.Write(info, 0, info.Length)
End Sub

Private Sub ProcessAllAssemblyOccurrences()
    Try
        Dim doc As AssemblyDocument = CType(ThisApplication.ActiveDocument, AssemblyDocument)
        Dim compDef As AssemblyComponentDefinition = CType(doc.ComponentDefinition, AssemblyComponentDefinition)
        Dim exportToExcel As Boolean = False
        Dim result As DialogResult = System.Windows.Forms.MessageBox.Show("Want to export the BOM Views to Excel now?", "Export? This will take a little while because Excel!", MessageBoxButtons.YesNo)
        If result = DialogResult.Yes Then
            exportToExcel = True
        End If

        RenumberBomViews(compDef, BOMLevels, exportToExcel)
        For Each assy As AssemblyDocument In AssySubAssemblies
            Try
				Dim ThisAssy As AssemblyDocument = assy
            	RenumberBomViews(ThisAssy.ComponentDefinition, True, exportToExcel)
			Catch AssyEx As Exception
				MessageBox.Show("Error ocurred in: " & assy.FullFileName & " Full Error Was: " & AssyEx.Stacktrace)
			End Try
        Next
    Catch ex As Exception
        MessageBox.Show(ex.Message)
    End Try
End Sub

Public Sub Updatestatusbar(ByVal message As String)
    ThisApplication.StatusBarText = message
End Sub

Public Sub Updatestatusbar(ByVal percent As Double, ByVal message As String)
    ThisApplication.StatusBarText = message & " (" + percent.ToString("P1") & ")"
End Sub

Private Sub RenumberBomViews(ByVal parentAssyCompDef As AssemblyComponentDefinition, ByVal BOMLevels As Boolean, ByVal Optional ExportToExcelNow As Boolean = False)
    Try
        Dim AssyBom As BOM = parentAssyCompDef.BOM
        Dim ParentAssyDoc As AssemblyDocument = CType(parentAssyCompDef.Document, AssemblyDocument)
        Dim ParentFolder As String = System.IO.Path.GetDirectoryName(ParentAssyDoc.FullFileName)
        Dim ExportedBOMFolder As String = System.IO.Path.Combine(ParentFolder, "04 Exported BOMs")
        Dim ExportedBOMFileName As String = System.IO.Path.Combine(ExportedBOMFolder, System.IO.Path.GetFileNameWithoutExtension(ParentAssyDoc.FullFileName) & ".xlsx")
        Dim CustomerName As String = System.IO.Path.GetFileName(ParentFolder)
        Dim BOMCustomFile As String = System.IO.Path.Combine(ParentFolder, CustomerName & "_BOM_Style.xml")
        AssyBom.ImportBOMCustomization(BOMCustomFile)
        If Not(AssyBom.StructuredViewEnabled = True) Then
            'Log.Info("structured bom view disabled: " & ParentAssyDoc.FullFileName)
        Else
            Updatestatusbar("Processing: " & ParentAssyDoc.FullFileName)
            If BOMLevels = False Then
                AssyBom.StructuredViewFirstLevelOnly = BOMLevels
            Else
                AssyBom.StructuredViewFirstLevelOnly = BOMLevels
            End If

            Dim ThisAssyBOMView As BOMView = AssyBom.BOMViews("Structured")
            RenumberBOMViewRows(ParentAssyDoc, ThisAssyBOMView.BOMRows)
            ThisAssyBOMView.Sort("Item", True)
            If ExportToExcelNow Then
                ThisAssyBOMView.Export(ExportedBOMFileName, FileFormatEnum.kMicrosoftExcelFormat)
            End If

            ThisAssyBOMView = AssyBom.BOMViews("Parts Only")
            RenumberBOMViewRows(ParentAssyDoc, ThisAssyBOMView.BOMRows)
            ThisAssyBOMView.Sort("Item", True)
        End If
    Catch ex As Exception
        MessageBox.Show("Error: " & ex.Message & " Ocurred in file: " & parentAssyCompDef.Document.FullFileName)
    End Try
End Sub

Private Sub RenumberBOMViewRows(ByVal parentAssyDoc As AssemblyDocument, ByVal BOMRows As BOMRowsEnumerator)
    Try
        For Each row As BOMRow In BOMRows
            Dim rowCompDef As ComponentDefinition = Row.ComponentDefinitions(1)
            Dim ThisDoc As Document = CType(rowCompDef.Document, Document)
            If row.Promoted Then
                'Log.Info(ThisDoc.FullFileName & " is Promoted!")
            End If

            Dim matchingStoredDocument As BomRowItem =(From item In ccBomRowItems Where item.Document = ThisDoc.FullFileName Select item).FirstOrDefault()
            If row.ChildRows IsNot Nothing Then
                RenumberBOMViewRows(CType(ThisDoc, AssemblyDocument), row.ChildRows)
            End If

            If matchingStoredDocument IsNot Nothing Then
                'Log.Info("Assembly: " & System.IO.Path.GetFileName(parentAssyDoc.FullFileName) & " | Part: " + System.IO.Path.GetFileName(ThisDoc.FullFileName) & " Item No changed from: " + row.ItemNumber & " to: " + matchingStoredDocument.ItemNo)
                row.ItemNumber = matchingStoredDocument.ItemNo
                matchingStoredDocument.Quantity = Convert.ToInt32(row.TotalQuantity)
                matchingStoredDocument.WhereUsed.Add(parentAssyDoc.FullFileName)
            Else
                If System.IO.Path.GetFileNameWithoutExtension(ThisDoc.FullFileName).StartsWith("COTS") Then
                    Dim COTSnumber As String = System.IO.Path.GetFileNameWithoutExtension(ThisDoc.FullFileName)
                    Dim partnumber As String = GetorSetStandardiProperty(ThisDoc, PropertiesForDesignTrackingPropertiesEnum.kPartNumberDesignTrackingProperties, "", "")
                    If Not(COTSnumber = partnumber) Then
                        COTSnumber = partnumber
                    End If

                    Dim COTSBase As Double = 0
                    Dim regex As Regex = New Regex("(\d{6}\w.*)|(\d{6})")
                    Dim f As String = String.Empty
                    f = regex.Match(COTSnumber).Captures(0).ToString()
                    Dim doubleValue As Double = 0
                    Dim COTSNum As Double = 0
                    Dim newItemNum As String = String.Empty
                    If Double.TryParse(f, doubleValue) Then
                        COTSBase = GetRoundNum(doubleValue, 100000)
                        COTSNum = Convert.ToDouble(f)
                        newItemNum = Convert.ToString(COTSNum - COTSBase)
                    Else
                        Dim pattern As String = "(\d{6})(\w.*)"
                        Dim matches As MatchCollection = Regex.Matches(f, pattern)
                        Dim prefix As String = matches(0).Groups(1).ToString()
                        Dim suffix As String = matches(0).Groups(2).ToString()
                        COTSBase = GetRoundNum(Convert.ToDouble(prefix), 100000)
                        COTSNum = Convert.ToDouble(prefix)
                        newItemNum = Convert.ToString(COTSNum - COTSBase) & suffix
                    End If

                    row.ItemNumber = newItemNum
                Else
                    If Not(SetorCreateCustomiProperty(ThisDoc, "ItemNo").ToString() = String.Empty) Then
						Try
                        	row.ItemNumber = SetorCreateCustomiProperty(ThisDoc, "ItemNo").ToString()
						Catch fileEx As Exception
							MessageBox.Show("iProperty probably missing error: " & fileEx.Message & "In file: " & ThisDoc.FullFileName)
						End Try
                    End If
                End If
            End If
        Next
    Catch ex As Exception
        MessageBox.Show("Error: " & ex.Message & " Ocurred in file: " & parentAssyDoc.FullFileName)
    End Try
End Sub

Private Function GetRoundNum(ByVal Number As Double, ByVal multiple As Integer) As Double
    Return Convert.ToInt32(Number / multiple) * multiple
End Function

Public Function GetiPropertyDisplayName(ByVal iProp As [Property]) As String
    Return iProp.DisplayName
End Function

Public Function GetiPropertyType(ByVal iProp As [Property]) As ObjectTypeEnum
    Return iProp.Type
End Function

Public Function GetiPropertyTypeString(ByVal iProp As [Property]) As String
    Dim valToTest As String = iProp.Value.ToString()
    Dim intResult As Integer
    If Integer.TryParse(valToTest, intResult) Then
        Return "Number"
    End If

    Dim doubleResult As Double
    If Double.TryParse(valToTest, doubleResult) Then
        Return "Number"
    End If

    Dim dateResult As System.DateTime
    If System.DateTime.TryParse(valToTest, dateResult) Then
        Return "Date"
    End If

    Dim booleanResult As Boolean
    If Boolean.TryParse(valToTest, booleanResult) Then
        Return "Boolean"
    End If

    Dim strResult As String = String.Empty
    If Not(iProp.Value.ToString() = String.Empty) Then
        Return "String"
    End If

    Return Nothing
End Function

Public Function GetorSetStandardiProperty(ByVal DocToUpdate As Inventor.Document, ByVal iPropertyTypeEnum As PropertiesForDesignTrackingPropertiesEnum, ByVal Optional newpropertyvalue As String = "", ByVal Optional propertyTypeStr As String = "") As String
    Dim invProjProperties As PropertySet = DocToUpdate.PropertySets("{32853F0F-3444-11D1-9E93-0060B03C1CA6}")
    Dim currentvalue As String = String.Empty
    If Not(newpropertyvalue = String.Empty) Then
        invProjProperties.ItemByPropId(CInt(iPropertyTypeEnum)).Value = newpropertyvalue.ToString()
    Else
        currentvalue = invProjProperties.ItemByPropId(CInt(iPropertyTypeEnum)).Value.ToString()
        newpropertyvalue = GetiPropertyDisplayName(invProjProperties.ItemByPropId(CInt(iPropertyTypeEnum)))
    End If

    If propertyTypeStr = String.Empty Then
        propertyTypeStr = GetiPropertyTypeString(invProjProperties.ItemByPropId(CInt(iPropertyTypeEnum)))
    End If

    Return currentvalue
End Function

Public Function SetorCreateCustomiProperty(ByVal Doc As Inventor.Document, ByVal PropertyName As String, ByVal Optional PropertyValue As Object = Nothing) As Object
    Try
        Dim customPropSet As PropertySet = Nothing
        Dim customproperty As Object = Nothing
        customPropSet = Doc.PropertySets("Inventor User Defined Properties")
        Dim prop As Inventor.[Property] = Nothing
        Dim propExists As Boolean = True
        Try
            prop = customPropSet(PropertyName)
        Catch ex As Exception
            MessageBox.Show(ex.Message)
            propExists = False
        End Try

        If(PropertyValue IsNot Nothing) Then
            If Not propExists Then
                prop = customPropSet.Add(PropertyValue, PropertyName)
            Else
                prop.Value = PropertyValue
            End If
        Else
            customproperty = prop.Value
        End If

        Return customproperty
    Catch mainEx As Exception
        MessageBox.Show("Error: " & mainEx.Message & "in file: " + Doc.FullFileName)
        Return Nothing
    End Try
End Function

Public Class BomRowItem

    Public Property ItemNo As String
        Get
            Return m_ItemNo
        End Get

        Set(ByVal value As String)
            m_ItemNo = value
        End Set
    End Property

    Private m_ItemNo As String

    Private m_occurrence As String

    Public Property Document As String
        Get
            Return m_occurrence
        End Get

        Set(ByVal value As String)
            m_occurrence = value
        End Set
    End Property

    Private m_Material As String

    Public Property Material As String
        Get
            Return m_Material
        End Get

        Set(ByVal value As String)
            m_Material = value
        End Set
    End Property

    Private m_Quantity As Integer

    Public Property Quantity As Integer
        Get
            Return m_Quantity
        End Get

        Set(ByVal value As Integer)
            m_Quantity = value
        End Set
    End Property

    Private m_WhereUsed As List(Of String)

    Public Property WhereUsed As List(Of String)
        Get
            Return m_WhereUsed
        End Get

        Set(ByVal value As List(Of String))
            m_WhereUsed = value
        End Set
    End Property
End Class
