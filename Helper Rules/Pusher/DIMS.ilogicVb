Sub Main()
	
    Dim oAsmDoc As Inventor.AssemblyDocument = ThisDoc.Document
	Dim trans As Transaction = ThisApplication.TransactionManager.StartTransaction(ThisDoc.Document, "Push Parameter Values to referenced documents")
    Try
		Dim oPars As Inventor.Parameters = oAsmDoc.ComponentDefinition.Parameters
	
		Dim oList As Collection = New Collection
		For Each oPar As Inventor.Parameter In oPars
			If (oPar.Name.StartsWith("A:")) Then
                oList.Add(oPar.Name)
            End If
		Next
	
		If oList.Count = 0 Then
			MsgBox("Empty list :(")
		Else
            For Each oDoc As Document In oAsmDoc.AllReferencedDocuments
                If Not oDoc.FullFileName.Contains("Content Center") Then 'not CC file
                    If oDoc.DocumentType = DocumentTypeEnum.kPartDocumentObject Then
                        Dim oPartDoc As PartDocument = oDoc
                        Dim partDef As ComponentDefinition = oPartDoc.ComponentDefinition
                        For Each ParName As String In oList
                            Try
                                Dim oParam As Parameter = partDef.Parameters(ParName)
                                oParam.Value = Parameter(ParName) / 10
                            Catch
                            End Try
                        Next
                    ElseIf oDoc.DocumentType = DocumentTypeEnum.kAssemblyDocumentObject Then
                        Dim oAssyDoc As AssemblyDocument = oDoc
                        Dim assyDef As ComponentDefinition = oAssyDoc.ComponentDefinition
                        For Each ParName As String In oList
                            Try
                                Dim oParam As Parameter = assyDef.Parameters(ParName)
                                oParam.Value = Parameter(ParName) / 10
                            Catch
                            End Try
                        Next
                    End If
                End If
            Next
        End If
	Catch ex As exception
		MessageBox.Show("Something is broken: " & ex.message & " " & ex.stacktrace)
		trans.abort()
	Finally
    'Update the document to see the changes
    iLogicVb.UpdateWhenDone = True
	trans.End()
	End Try
End Sub
