Option Explicit On
AddReference "IlogicExternalDebug.dll"
Imports iLogicExternalDebug
Imports System.IO
'Imports Microsoft.office.interop.excel
Private Sub Main()
    xtClass.ThisApplication = ThisApplication
    xtClass.DocToUpdate = ThisDoc
    'Call xtClass.SaveCopyAsFromBrowserNodeNames
    'Call insertdummyfiles
	'Call xtclass.CheckiPartTableForErrors
	Call xtclass.beginaligndrawingviews
End Sub
Public xtClass As New iLogicExternalDebug.ExtClass()
