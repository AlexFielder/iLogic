AddReference "System.Drawing"

Imports System.Windows.Forms
Imports System.Drawing
imports System.Linq
''' <summary>
''' based on the code from here: 
''' http://spiderinnet2.typepad.com/blog/2013/09/inventor-net-ui-miscellaneous-dockablewindow.html
''' </summary>
 Public Sub Main()
	CreateDockableWindow(ThisApplication)
End Sub

''' <summary>
''' creates a new System.Windows.Forms.Form object and returns its handle so it can
''' be used in a newly created DockableWindow object
''' </summary>
''' <returns>the Long of the new Windows form</returns>
 Public Function CreateChildDialog() As Long
	Dim textSize As Size = Nothing
    Dim dc As Form = New Form()
	dc.AutoScaleDimensions = New System.Drawing.SizeF(6.0!, 13.0!)
	dc.AutoScaleMode = System.Windows.Forms.AutoScaleMode.Font
    dc.Text = "Child Dialog"
    dc.HelpButton = CSharpImpl.__Assign(dc.MinimizeBox, CSharpImpl.__Assign(dc.MaximizeBox, False))
    dc.ShowIcon = CSharpImpl.__Assign(dc.ShowInTaskbar, False)
	dc.ControlBox = False
	dc.FormBorderStyle = 0
    dc.TopMost = True
    dc.Height = 100
    dc.Width = 300
    dc.MinimumSize = New Size(dc.Width, dc.Height)
    Dim margin As Integer = 5
    Dim size As Size = dc.ClientSize
    Dim tb As System.Windows.Forms.TextBox = New System.Windows.Forms.TextBox()
    tb.TextAlign = HorizontalAlignment.Right
    tb.Height = 20
    tb.Width = size.Width - 2 * margin
    tb.Location = New System.Drawing.Point(margin, margin)
    tb.Anchor = AnchorStyles.Top Or AnchorStyles.Left Or AnchorStyles.Right
    dc.Controls.Add(tb)
	'Designation
	Dim lblDesignation As Label = New Label
	lblDesignation.Text = "Designation:"
	lblDesignation.Location = New System.Drawing.Point(margin, margin + 30 + 2.5)
	lblDesignation.Anchor = AnchorStyles.Top Or AnchorStyles.Left Or AnchorStyles.Right
	lblDesignation.AutoSize = True
	lblDesignation.Size = New System.Drawing.Size(66, 13)
	dc.Controls.Add(lblDesignation)
	Dim cbBoxDesignation As ComboBox = New ComboBox
	cbBoxDesignation.Text = "Designation"
	cbBoxDesignation.Location = New System.Drawing.Point(((size.Width * 0.25)) + margin, margin + 30)
	cbBoxDesignation.Anchor = AnchorStyles.Top Or AnchorStyles.Left Or AnchorStyles.Right
	cbBoxDesignation.Width = (size.Width * 0.75) - 2 * margin
	dc.Controls.Add(cbBoxDesignation)
	'Length
	Dim lblLength As Label = New Label
	lblLength.Text = "Length:"
	lblLength.Location = New System.Drawing.Point(margin, lblDesignation.Location.Y + 30)
	lblLength.Anchor = AnchorStyles.Top Or AnchorStyles.Left Or AnchorStyles.Right
	lblLength.AutoSize = True
	lblLength.Size = New System.Drawing.Size(66, 13)
	dc.Controls.Add(lblLength)
	Dim cbBoxLength As ComboBox = New ComboBox
	cbBoxLength.Text = "Length"
	cbBoxLength.Location = New System.Drawing.Point(((size.Width * 0.25)) + margin, cbBoxDesignation.Location.Y + 30)
	cbBoxLength.Anchor = AnchorStyles.Top Or AnchorStyles.Left Or AnchorStyles.Right
	cbBoxLength.Width = (size.Width * 0.75) - 2 * margin
	dc.Controls.Add(cbBoxLength)
	'Diameter
	Dim lblDiameter As Label = New Label
	lblDiameter.Text = "Diameter:"
	lblDiameter.Location = New System.Drawing.Point(margin, lblLength.Location.Y + 30)
	lblDiameter.Anchor = AnchorStyles.Top Or AnchorStyles.Left Or AnchorStyles.Right
	lblDiameter.AutoSize = True
	lblDiameter.Size = New System.Drawing.Size(43, 13)
	dc.Controls.Add(lblDiameter)
	Dim cbBoxDiameter As ComboBox = New ComboBox
	cbBoxDiameter.Text = "Diameter"
	cbBoxDiameter.Location = New System.Drawing.Point(((size.Width * 0.25)) + margin, cbBoxLength.Location.Y + 30)
	cbBoxDiameter.Anchor = AnchorStyles.Top Or AnchorStyles.Left Or AnchorStyles.Right
	cbBoxDiameter.Width = (size.Width * 0.75) - 2 * margin
	dc.Controls.Add(cbBoxDiameter)
	buttonExample = New Button
	buttonExample.Text = "Click Me."
	buttonExample.Location = New System.Drawing.Point(((size.Width * 0.25)) + margin, cbBoxDiameter.Location.Y + 30)
	buttonExample.Anchor = AnchorStyles.Top Or AnchorStyles.Left Or AnchorStyles.Right
	buttonExample.Width = (size.Width * 0.75) - 2 * margin
	dc.Controls.Add(buttonExample)
	'display form
    dc.Show()
	break
    Return dc.Handle.ToInt64()
End Function

Public WithEvents buttonExample As Button

Function measureText(stringtoMeasure As String) As Size
	Dim arialBold = New Font("Arial", 6.0F)
	Dim textSize As Size = TextRenderer.MeasureText(stringtoMeasure, arialBold)
End Function

''' <summary>
''' Creates a new DockableWindow object
''' </summary>
''' <param name="app"></param>
 Public Sub CreateDockableWindow(ByVal app As Inventor.Application)
'	 Logger.Debug("made it this far")
	Dim dockableWinInternalName As String = "My_Example_Dockable_Window"
    Dim uiMan As UserInterfaceManager = app.UserInterfaceManager
	Dim dockableWin As DockableWindow = (From win As DockableWindow In uiMan.DockableWindows
											Where win.Internalname.ToUpper() = dockableWinInternalName.ToUpper()
											Select win).FirstOrDefault()
	If Not dockableWin Is Nothing Then
'		Break
		dockableWin.Delete
	Else
		Logger.Debug("no existing DockableWindow found")
	End If
    dockableWin = uiMan.DockableWindows.Add(Guid.NewGuid().ToString(), dockableWinInternalName, "DockableWindow #1")
    dockableWin.AddChild(CreateChildDialog())
    dockableWin.DisabledDockingStates = DockingStateEnum.kDockLeft Or DockingStateEnum.kDockTop
    dockableWin.DockingState = DockingStateEnum.kDockLastKnown
    dockableWin.ShowVisibilityCheckBox = True
    dockableWin.ShowTitleBar = True
    dockableWin.SetMinimumSize(100, 100)
    dockableWin.Visible = True
End Sub

Public Sub ButtonClick(ByVal sender As System.Object, ByVal e As System.EventArgs) Handles buttonExample.Click
	MessageBox.Show("Hello World.")
	ThisApplication.Documents.Add(DocumentTypeEnum.kPartDocumentObject)
	' iLogicVb.RunExternalRule("TFI Dome thingy")
End Sub

 Private Class CSharpImpl
    <Obsolete("Please refactor calling code to use normal Visual Basic assignment")>
    Shared Function __Assign(Of T)(ByRef target As T, value As T) As T
        target = value
        Return value
    End Function
End Class
