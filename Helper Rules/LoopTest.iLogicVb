''' <summary>
''' uses c# code from here: https://stackoverflow.com/a/19347286/572634
''' </summary>
Public Sub Main()
	For i = 1 To 10
		call runloop()
	Next i
End Sub

Public Sub runloop()
    Dim watch = New Stopwatch()
'	Dim array As Integer() = New Integer(99999999) {}
    Dim array As Long() = New Long(99999999) {}

    For i As Long = 0 To array.LongLength - 1
        array(i) = 1
    Next

    watch.Restart()
    Dim sum As Long = 0

    For i As Long = 0 To array.LongLength - 1
        sum += array(i)
    Next

    Logger.Debug("for loop:" & watch.ElapsedMilliseconds.ToString() & "ms, result:" + sum.ToString())
    sum = 0
    watch.Restart()
    sum = array.Sum()
    Logger.Debug("linq sum:" & watch.ElapsedMilliseconds.ToString() & "ms, result:" + sum.ToString())
    sum = 0
    watch.Restart()
    Dim length As Long = array.LongLength

    For i As Long = 0 To length - 1
        sum += array(i)
    Next

    Logger.Debug("for loop fixed:" & watch.ElapsedMilliseconds.ToString() & "ms, result:" + sum.ToString())
    sum = 0
    watch.Restart()

    For Each i As Long In array
        sum += i
    Next

    Logger.Debug("foreach sum:" & watch.ElapsedMilliseconds.ToString() & "ms, result:" + sum.ToString())
    sum = 0
    watch.Restart()
    sum = array.AsParallel().Sum()
    Logger.Debug("linq parallel sum:" & watch.ElapsedMilliseconds & "ms, result:" + sum.ToString())
End Sub
