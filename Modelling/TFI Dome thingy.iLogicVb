Option Explicit On
Imports System.Linq
Imports System.Collections.Generic

''' <summary>
''' Inspired by this video by TFICADTips: https://www.youtube.com/watch?v=aq8rRc9H_TI
''' </summary>
Public Sub Main()
If ThisApplication.ActiveDocument.DocumentType = DocumentTypeEnum.kPartDocumentObject Then
	Dim trans As Transaction = ThisApplication.TransactionManager.StartTransaction(ThisApplication.ActiveDocument, "TFI Dome Thingy")
	Try
	CreateDome(ThisApplication.ActiveDocument)
	trans.End()
	Catch ex As Exception
		trans.Abort
		MessageBox.Show("the error was: " & ex.Message)
	End Try
Else
	MsgBox("This rule does not work in an Assembly!")
End If
End Sub
'public reusable objects
Public OriginSketchPoint As SketchPoint = Nothing
Public transObjs As TransientObjects = Nothing
Public transGeom As TransientGeometry = Nothing
Public debuggingGraphics As ClientGraphics = Nothing
Public workplaneCollection As ObjectCollection = Nothing
Public sculptSurfaceCollection As ObjectCollection = Nothing
'change this to draw graphics:
Public debugging As Boolean = true 'False
Public Tolerance As Double = 1E-12

''' <summary>
''' Lets us create the "Geodesic"(?) dome featured in the video linked above.
''' </summary>
''' <param name="PartDoc"></param>
''' <param name="Diameter"></param>
Public Sub CreateDome(ByVal PartDoc As Document, Optional Diameter As String = "4m")
	Dim NumSides As Integer = 6 'this could be an input from the user so long as it's an even number!? but will take some work using angles to properly configure!
	Dim partCompDef As PartComponentDefinition = PartDoc.ComponentDefinition
	'set up public (shared) objects
	transObjs = ThisApplication.TransientObjects
	transGeom = ThisApplication.TransientGeometry
	debuggingGraphics = DrawingDebuggingGraphics(partCompDef)
	Dim Sketch1 As PlanarSketch = CreateSketch(partCompDef, partCompDef.WorkPlanes(3))
'	p = Parameter.Param("d0")
	'add a diameter parameter
	Dim userParams As UserParameters = partCompDef.Parameters.UserParameters
	Dim diamParam As Parameter = Nothing
	Try
	diamParam = Parameter.Param("diameter")
	Catch
		diamParam = userParams.AddByExpression("diameter", "4m", UnitsTypeEnum.kMillimeterLengthUnits)
	End Try
	If diamParam Is Nothing Then
		If Not diamParam.Param.InUse Then
			userParams.Item("diameter").Delete()
			diamParam = userParams.AddByExpression("diameter", Diameter, UnitsTypeEnum.kMillimeterLengthUnits)
		End If
	End If
	Sketch1.SketchLines.AddAsPolygon(NumSides, OriginSketchPoint, transGeom.CreatePoint2d(diamParam.Value() / 2), True)
	
	'ADD Constraints to polygon:
	'ADD COINCIDENT CONSTRAINT BETWEEN RECTANGLE CENTRE AND ORIGIN
	Dim PolygonCentrePoint As SketchPoint = Sketch1.SketchPoints(2)
	Sketch1.GeometricConstraints.AddCoincident(PolygonCentrePoint, OriginSketchPoint)
	Dim PolygonVerticalPoint As SketchPoint = Sketch1.SketchLines(2).EndSketchPoint ' Sketch1.SketchPoints(5)
	Sketch1.GeometricConstraints.AddVerticalAlign(PolygonVerticalPoint, OriginSketchPoint)
	Dim oConstraint As TwoPointDistanceDimConstraint
	Dim TextPoint As Point2d = transGeom.CreatePoint2d(0, ((Parameter("diameter") /10)+10) / 2)
	oConstraint = Sketch1.DimensionConstraints.AddTwoPointDistance(Sketch1.SketchLines(1).StartSketchPoint, 
																	Sketch1.SketchLines(4).EndSketchPoint, 
																	DimensionOrientationEnum.kHorizontalDim, 
																	TextPoint, 
																	False)
	oConstraint.Parameter.Expression = "diameter"
	Sketch1.SetEndOfPart(True)
	Sketch1.Visible = False
	partCompDef.SetEndOfPartToTopOrBottom(False)
	'DebugSketchPointsEtc(Sketch1)
	OriginSketchPoint = Nothing
	'offset workplane and sketch 2
	Dim OffsetWorkPlane As WorkPlane = partCompDef.WorkPlanes.AddByPlaneAndOffset(partCompDef.WorkPlanes(3), (Parameter("diameter") / 10) / 2)
	OffsetWorkPlane.Visible = False
	Dim latestParam As ModelParameter = GetLatestModelParameter(partCompDef)
	latestParam.Name = "height"
	workplaneCollection = transObjs.CreateObjectCollection()
	sculptSurfaceCollection = transObjs.CreateObjectCollection()
	'add XY plane
	'these might need tweaking:
	sculptSurfaceCollection.Add(createSculptSurfaceForCollection(partCompDef, partCompDef.WorkPlanes(3), PartFeatureExtentDirectionEnum.kPositiveExtentDirection))
	sculptSurfaceCollection.Add(createSculptSurfaceForCollection(partCompDef, OffsetWorkPlane, PartFeatureExtentDirectionEnum.kNegativeExtentDirection))
	'workplaneCollection.Add(partCompDef.WorkPlanes(3))
	'add new workplane
	workplaneCollection.Add(OffsetWorkPlane)
	partCompDef.WorkPlanes(3).Visible = True
	OffsetWorkPlane.Visible = True
	
	Dim Sketch2 As PlanarSketch = CreateSketch(partCompDef, OffsetWorkPlane)
	Sketch2.SketchLines.AddAsPolygon(numsides, OriginSketchPoint, transGeom.CreatePoint2d(diamParam.Value() / 2), True)
	PolygonCentrePoint = Sketch2.SketchPoints(2)
	
	Sketch2.GeometricConstraints.AddCoincident(PolygonCentrePoint, OriginSketchPoint)
	Dim PolygonHorizontalPoint As SketchPoint = Sketch2.SketchLines(1).EndSketchPoint
	Sketch2.GeometricConstraints.AddHorizontalAlign(PolygonHorizontalPoint, OriginSketchPoint)
	TextPoint = transGeom.CreatePoint2d(((Parameter("diameter") / 10) + 10) / 2, 0)
	oConstraint = Sketch2.DimensionConstraints.AddTwoPointDistance(Sketch2.SketchLines(1).StartSketchPoint, 
																	Sketch2.SketchLines(3).StartSketchPoint, 
																	DimensionOrientationEnum.kVerticalDim, 
																	TextPoint, 
																	False)
	Sketch2.Visible = False
	oConstraint.Parameter.Expression = "diameter"
'	If debugging Then
'		DebugSketchPointsEtc(Sketch2)
'	End If
	Sketch2.SetEndOfPart(True)
	partCompDef.SetEndOfPartToTopOrBottom(False)
	'calculate centre and endpoints of lines for new workplane set:
	Dim Sketch1CornerPoints As List(Of SketchPoint) = (From skline As SketchLine In Sketch1.SketchLines
													Select skLine.StartSketchPoint).ToList()
	Dim Sketch1MidPoints As List(Of SketchPoint) = (From skline As SketchLine In Sketch1.SketchLines
													Let midpoint As SketchPoint = GetSketchLineMidPoint(skline)
													Select midpoint).Tolist()
	
	Dim Sketch2CornerPoints As List(Of SketchPoint) = (From skline As SketchLine In Sketch2.SketchLines
													Select skLine.StartSketchPoint).ToList()
	
	Dim Sketch2MidPoints As List(Of SketchPoint) = (From skline As SketchLine In Sketch2.SketchLines
													Let midpoint As SketchPoint = GetSketchLineMidPoint(skline)
													Select midpoint).Tolist()
	
	Create3PointWorkplaneFromList(partCompDef, CalculateGroupsOfPointsForWorkplanes(Sketch1, Sketch2CornerPoints, Sketch1CornerPoints), False)
	Create3PointWorkplaneFromList(partCompDef, CalculateGroupsOfPointsForWorkplanes(Sketch2, Sketch1CornerPoints, Sketch2CornerPoints), True)
	
	Dim sculpt1 As SculptFeature = partCompDef.Features.SculptFeatures.Add(sculptSurfaceCollection, PartFeatureOperationEnum.kNewBodyOperation)
	Dim body As SurfaceBody = sculpt1.SurfaceBodies(1)
	
	sculptSurfaceCollection.Clear()
	
'	If debugging Then
'		body.Visible = False
'	End If
	Dim specificPointGroups As List(Of PointsForSolidPlanes) = GetSpecificPointGroups(Sketch2, Sketch2MidPoints, NumSides, Tolerance)
	Dim matchingPoints As List(Of PointsForSolidPlanes) = GetMatchingSketchPointForMid(Sketch1, specificPointGroups, Sketch1CornerPoints)
	workplaneCollection.Clear()

	Create3PointWorkplaneFromList(partCompDef, matchingPoints, True, True, True)
	
	Dim topAxis1 As WorkAxis = Nothing
	Dim topAxis2 As WorkAxis = Nothing
'	MessageBox.Show(workplaneCollection.Count)
Break
	Dim Zaxis As WorkAxis = partCompDef.WorkAxes.Item(3)
Break	
	For Each ws As WorkPlane In workplaneCollection
			If topAxis1 Is Nothing Then
				topAxis1 = partCompDef.WorkAxes.AddByLineAndPlane(Zaxis, ws)
			Else
				topAxis2 = partCompDef.WorkAxes.AddByLineAndPlane(Zaxis, ws)
			End If
			ws.Visible = False
	Next
	
	Dim topPoint As WorkPoint = partCompDef.WorkPoints.AddByTwoLines(topAxis1, topAxis2)
	topAxis1.Visible = False
	topAxis2.Visible = False
	toppoint.Visible = False
	sculptSurfaceCollection.Clear()
	'need to create a workplane between the new point ^ and the cornerpoints of sketch two
	Create3PointWorkplaneFromList(partCompDef, CalculateGroupsOfPointsForWorkplanes(Sketch2, Sketch2CornerPoints, topPoint), False)
	Dim sculpt2 As SculptFeature = partCompDef.Features.SculptFeatures.Add(sculptSurfaceCollection, PartFeatureOperationEnum.kJoinOperation)
	
End Sub

''' <summary>
''' Sorts out the grouping by checking for shortest lines with matching endpoints.
''' </summary>
''' <param name="thissketch"></param>
''' <param name="pointGroups"></param>
''' <returns>Returns the completed pointsforSolidPlanes grouping including the relevant sketchpoint for workplane creation.</returns>
Public Function GetMatchingSketchPointForMid(ByVal thissketch As PlanarSketch,
											ByVal pointGroups As List(Of PointsForSolidPlanes), 
											ByVal cornerpoints As List(Of SketchPoint)) As List(Of PointsForSolidPlanes)

	For Each pointgrp As PointsForSolidPlanes In pointGroups
		Dim linegroups As List(Of LineGroup)
		pointgrp.startPointLines = New List(Of LineSegment)
		pointgrp.EndPointLines = New List(Of LineSegment)
		For Each skline As SketchLine In thissketch.sketchlines
			Dim startPoint As Point = skline.Geometry3d.StartPoint
			Dim endPoint As Point = skline.Geometry3d.EndPoint
			pointgrp.startPointLines.Add(transGeom.CreateLineSegment(startPoint, pointgrp.StartPoint.Geometry3d ))
			pointgrp.EndPointLines.Add(transGeom.CreateLineSegment(startPoint, pointgrp.EndPoint.Geometry3d))
		Next
'Break
		Dim midpoint As SketchPoint = (From skp As SketchPoint In cornerpoints
										From startln As LineSegment In pointgrp.startPointLines
										From endln As LineSegment In pointgrp.EndPointLines
										Where startln.endpoint.isequalto(endln.endpoint, Tolerance) And skp.geometry3d.isequalto(startln.endpoint)
										Select skp).firstordefault()
'Break											
		Dim lineswithsameendpointsandlengths As List(Of LineSegment)= (From startln As LineSegment In pointgrp.startPointLines
																From endln As LineSegment In pointgrp.EndPointLines
																Where startln.startpoint.IsEqualto(endln.startpoint, Tolerance) And IsEqual(getLineSegmentLength(startln), getLineSegmentLength(endln), Tolerance)
																Select startln).ToList()
'Break
		'should be only one line after this:
		lineswithsameendpointsandlengths = GetShortestLines(lineswithsameendpointsandlengths, Tolerance)
'		pointgrp.startPointLines = GetShortestLines(pointgrp.startPointLines, Tolerance)
'		pointgrp.EndPointLines = GetShortestLines(pointgrp.EndPointLines, Tolerance)
'		MessageBox.Show("line count: " & lineswithsameendpointsandlengths.Count)
		Dim midpointline As LineSegment = lineswithsameendpointsandlengths.Item(0)
		Dim midpointsketchpoint As SketchPoint = (From skp As SketchPoint In cornerpoints
								Where skp.geometry3d.isequalto(midpointline.startPoint, Tolerance)
								Select skp).firstordefault

		If Not midpointsketchpoint Is Nothing Then
			pointgrp.MidPoint = midpointsketchpoint
		Else
			messagebox.Show("No midpoint")
		End If
	Next
	Return pointGroups
End Function										

''' <summary>
''' Gets points grouped together based on the number of sides in our polygon.
''' </summary>
''' <param name="thisSketch"></param>
''' <param name="sketchpoints"></param>
''' <param name="sides"></param>
''' <param name="Tolerance"></param>
''' <returns></returns>
Public Function GetSpecificPointGroups(ByVal thisSketch As PlanarSketch, ByVal sketchpoints As List(Of SketchPoint), ByVal sides As Integer, ByVal Tolerance As Double) As List(Of PointsForSolidPlanes)
	Dim pointsforPlanes As List(Of PointsForSolidPlanes) = New List(Of PointsForSolidPlanes)
	Dim group1 As PointsForSolidPlanes = New PointsForSolidPlanes
	Dim group2 As PointsForSolidPlanes = New PointsForSolidPlanes

	For i As Integer = 1 To thisSketch.Sketchlines.Count
		Dim skline As SketchLine = thisSketch.Sketchlines(i)
		Dim skpoint As SketchPoint = (From sk As SketchPoint In sketchpoints
													Where sk.Geometry3d.IsEqualto(skline.Geometry3d.MidPoint, Tolerance)
													Select sk).FirstorDefault
		Select Case sides
			Case 6
				If i = 1 Then
					If Not skpoint Is Nothing Then
						group1.StartPoint = skpoint
					End If
				Else If i = 3 Then
					If Not skpoint Is Nothing Then
						group1.EndPoint = skpoint
					End If
				Else If i = 4 Then 
					If Not skpoint Is Nothing Then
						group2.StartPoint = skpoint
					End If
				Else If i = 6 Then
					If Not skpoint Is Nothing Then
						group2.EndPoint = skpoint
					End If					
				End If
			Case 8
					
			Case 10
						
			Case Else
		End Select
	Next
	Dim points As List(Of PointsForSolidPlanes) = New List(Of PointsForSolidPlanes)
	points.Add(group1)
	points.Add(group2)
'	break
	Return points
End Function

Public Function GetSpecificSketchLineMidPoints(ByVal thisSketch As Sketch, ByVal sketchmidpoints As List(Of SketchPoint), ByVal sides As Integer, ByVal Tolerance As Double) As List(Of SketchPoint)
	Dim sketchpoints As List(Of SketchPoint) = New List(Of SketchPoint)
	For i As Integer = 1 To thisSketch.Sketchlines.Count
		Dim skline As SketchLine = thisSketch.Sketchlines(i)
		Select Case sides
			Case 6
				If i = 1 Or i = 3 Or i = 4 Or i = 6 Then
					Dim skpoint As SketchPoint = (From sk As SketchPoint In sketchmidpoints
													Where sk.Geometry3d.IsEqualto(skline.Geometry3d.MidPoint, Tolerance)
													Select sk).FirstorDefault
					If Not skpoint Is Nothing Then
						sketchpoints.Add(skpoint)
					End If
				End If
			Case 8
					
			Case 10
						
			Case Else
				
		End Select
	Next
	If debugging Then
		DebugSketchPointsEtc(thisSketch, True, sketchpoints)
	End If
	Return sketchpoints
End Function

''' <summary>
''' creates a new sculpt surface for adding to our collection
''' </summary>
''' <param name="partCompDef"></param>
''' <param name="surfaceToAdd"></param>
''' <param name="direction"></param>
''' <returns></returns>
Public Function createSculptSurfaceForCollection(ByVal partCompDef As PartComponentDefinition, ByVal surfaceToAdd As Object, ByVal direction As PartFeatureExtentDirectionEnum ) As SculptSurface
	Dim sculpt1Surface As SculptSurface = partCompDef.Features.SculptFeatures.CreateSculptSurface(surfaceToAdd, direction)
	Return sculpt1Surface
End Function

''' <summary>
''' Creates a workplane from the supplied list, flips normal if required and adds the resultant sculpt surface to the collection for future use
''' </summary>
''' <param name="partCompDef"></param>
''' <param name="pointlist"></param>
''' <param name="FlipNormals"></param>
Public Sub Create3PointWorkplaneFromList(ByVal partCompDef As PartComponentDefinition, ByVal pointlist As List(Of PointsForSolidPlanes), ByVal FlipNormals As Boolean, Optional addToSculptcollection As Boolean = True, Optional addToWorksurfaceCollection As Boolean = False)
'break
	For Each pointset As PointsForSolidPlanes In pointlist
		Dim workplaneToAddForSculpt As WorkPlane = Nothing
		If pointset.MidPoint Is Nothing And Not pointset.MidWorkPoint Is Nothing Then
			workplaneToAddForSculpt = partCompDef.Workplanes.AddByThreePoints(pointset.StartPoint, pointset.MidWorkPoint, pointset.EndPoint)
		Else
			workplaneToAddForSculpt = partCompDef.Workplanes.AddByThreePoints(pointset.StartPoint, pointset.MidPoint, pointset.EndPoint)
		End If
		If FlipNormals Then
			workplaneToAddForSculpt.FlipNormal()
		End If
		workplaneToAddForSculpt.AutoResize = True
		If addToSculptcollection Then
			sculptSurfaceCollection.Add(createSculptSurfaceForCollection(partCompDef, workplaneToAddForSculpt, PartFeatureExtentDirectionEnum.kNegativeExtentDirection))
		End If
		If addToWorksurfaceCollection Then
			workplaneCollection.Add(workplaneToAddForSculpt)
		End If
	Next
	'MessageBox.Show("workplane collection count: " & workplanecollection.Count)
End Sub

Public Function CalculateGroupsOfPointsForWorkplanes(ByVal Sketch As PlanarSketch, 
														ByVal cornerpoints As List(Of SketchPoint),
														ByVal point As WorkPoint) As List(Of PointsForSolidPlanes)
	Dim listOfPoints As List(Of PointsForSolidPlanes) = New List(Of PointsForSolidPlanes)
	For Each Line As SketchLine In Sketch.sketchlines
		Dim pointgrp As PointsForSolidPlanes = New PointsForSolidPlanes
		pointgrp.StartPoint = Line.StartSketchPoint
		pointgrp.EndPoint = Line.EndSketchPoint
		pointgrp.MidWorkPoint = point
		listOfPoints.Add(pointgrp)
	Next
	Return listOfPoints
End Function

''' <summary>
''' Calculates groups of points for creation of workplanes
''' </summary>
''' <param name="Sketch"></param>
''' <param name="cornerpoints"></param>
''' <param name="endpoints"></param>
''' <returns></returns>
Public Function CalculateGroupsOfPointsForWorkplanes(ByVal Sketch As PlanarSketch, 
														ByVal cornerpoints As List(Of SketchPoint), 
														ByVal endpoints As List(Of SketchPoint)) As List(Of PointsForSolidPlanes)
	
	Dim listOfPoints As List(Of PointsForSolidPlanes) = New List(Of PointsForSolidPlanes)
	Dim lineGrouplist As List(Of LineGroup) = New List(Of LineGroup)
	For Each skLine As SketchLine In Sketch.SketchLines
		Dim thisLineGroup As LineGroup = New LineGroup
'		Break

		thisLineGroup.parentLine = skLine
		thisLineGroup.startPointLines = New List(Of LineSegment)
		thisLineGroup.EndPointLines = New List(Of LineSegment)
		
		Dim startPoint As Point = skLine.Geometry3d.StartPoint
		Dim endPoint As Point = skLine.Geometry3d.EndPoint

		For Each secondSketchCornerpoint As SketchPoint In cornerpoints
			thisLineGroup.startPointLines.Add(transGeom.CreateLineSegment(startPoint, secondSketchCornerpoint.Geometry3d))
			thisLineGroup.EndPointLines.Add(transGeom.CreateLineSegment(endPoint, secondSketchCornerpoint.Geometry3d))
		Next

		thisLineGroup.startPointLines = GetShortestLines(thisLineGroup.startPointLines, Tolerance)
		thisLineGroup.EndPointLines = GetShortestLines(thisLineGroup.EndPointLines, Tolerance)
		
		'debugging:
		If debugging Then
'			DrawDebugGraphicsLineList(thisLineGroup.startPointLines, GetColourFromString("blue"))
'			DrawDebugGraphicsLineList(thisLineGroup.EndPointLines, GetColourFromString("red"))
		End If
		lineGrouplist.Add(thisLineGroup)
	Next
'	MessageBox.Show("Count of lines: " & lineGrouplist.Count)

	For Each lineGrp As LineGroup In lineGrouplist
		Dim thesePoints As PointsForSolidPlanes = New PointsForSolidPlanes
		thesePoints.StartPoint = lineGrp.parentLine.StartSketchPoint
		thesePoints.EndPoint = lineGrp.parentLine.EndSketchPoint
		Dim startPointPoints As List(Of Point) = (From startline As LineSegment In lineGrp.startPointLines
													Let pnt As Point = startline.EndPoint
													Select pnt).toList()
		Dim endPointPoints As List(Of Point) = (From endline As LineSegment In lineGrp.EndPointLines
													Let pnt As Point = endline.EndPoint
													Select pnt).toList()
		If Not startPointPoints Is Nothing And Not endPointPoints Is Nothing Then
'			MessageBox.Show("Count of start Points = " & startPointPoints.Count & vbCrLf & "Count of end Points = " & endPointPoints.Count)
			Dim matchingpoints As List(Of SketchPoint) = New List(Of SketchPoint)
			For Each startPointPoint As Point In startPointPoints
				For Each endPointPoint As Point In endPointPoints
'					MessageBox.Show(startPointPoint.X & "," & startPointPoint.Y & "," & startPointPoint.Z & vbCrLf & _
'									endPointPoint.X & "," & endPointPoint.Y & "," & endPointPoint.Z)
					If startPointPoint.IsEqualTo(endPointPoint) Then ', Tolerance) Then
						'the points match, but we need the sketchpoint
'						Break
						For Each endpoint As SketchPoint In cornerpoints
							If endpoint.Geometry3d.IsEqualTo(startPointPoint, Tolerance) Then
								thesePoints.MidPoint = endpoint
							End If
						Next
'						thesePoints.MidPoint = (From pnt As SketchPoint In endpoints
'												Where pnt.Geometry3d.IsequalTo(startPointPoint)
'												Select pnt).firstOrdefault()
						If thesePoints.midpoint is Nothing Then
							'MessageBox.Show("No midpoint found!")
						Else
							listOfPoints.Add(thesePoints) 'matchingpoints.Add(startPointPoint)		
						end if
					End If
				Next
			Next
		End If
'		thesePoints.MidPoint = 
	Next

	Return listOfPoints
End Function

''' <summary>
''' Gets the shortest lines from a list of lines according to the tolerance provided.
''' </summary>
''' <param name="listofLines"></param>
''' <param name="tolerance"></param>
''' <returns></returns>
Public Function GetShortestLines(ByVal listofLines As List(Of LineSegment), ByVal tolerance As Double) As List(Of LineSegment)
	Dim min As Double = listofLines.Min(Function(entry As LineSegment) getLineSegmentLength(entry))
	If Not min = Nothing Then
		listofLines = listofLines.Where(Function (entry As LineSegment) IsEqual(getLineSegmentLength(entry), min, Tolerance)).ToList()
	End If
	Return listofLines
End Function

Public Function GetShortestLinesWithAdjoiningEndpoints(ByVal listoflines As List(Of LineGroup), ByVal tolerance As Double) As List(Of PointsForSolidPlanes)
	
'	Dim groupedbylength As List(Of LineSegment) = listoflines.groupby(Function(entry As LineSegment) getLineSegmentLength(entry)).ToList()
	Dim listofpoints As List(Of PointsForSolidPlanes) = New List(Of PointsForSolidPlanes)
	
	
	Return listofpoints
'	listoflines = listoflines.where(Function (entry As LineSegment) IsEqual(getLineSegmentLength(entry), Min))
End Function

''' <summary>
''' Returns the measured length between the start/end of a lineSegment object
''' </summary>
''' <param name="lineToMeasure"></param>
''' <returns></returns>
Public Function getLineSegmentLength(ByVal lineToMeasure As LineSegment) As Double
	Return ThisApplication.MeasureTools.GetMinimumDistance(lineToMeasure.StartPoint,lineToMeasure.EndPoint)
End Function

'Public Function GetCommonPoints(ByVal firstCollection As List(Of Point), ByVal secondCollection As List(Of Point), ByVal Tolerance As Double) As List(Of Point)
'    Dim hashSet = New HashSet(Of Point)(firstCollection.Cast(Of Point)(), New PointComparer(Tolerance))
'    hashSet.IntersectWith(secondCollection.Cast(Of Point)())
'    Return hashSet
'End Function

''' <summary>
''' Populates our public object
''' </summary>
Public Function DrawingDebuggingGraphics(ByVal partCompDef As PartComponentDefinition) As ClientGraphics
    Dim NewDebuggingGraphics = Nothing

    Try
        NewDebuggingGraphics = partCompDef.ClientGraphicsCollection("debuggingGraphics")
        If NewDebuggingGraphics IsNot Nothing Then
            NewDebuggingGraphics.Delete()
            NewDebuggingGraphics = partCompDef.ClientGraphicsCollection.Add("debuggingGraphics")
        End If
		Return NewDebuggingGraphics
    Catch __unusedException1__ As Exception
        NewDebuggingGraphics = partCompDef.ClientGraphicsCollection.Add("debuggingGraphics")
		Return NewDebuggingGraphics
    End Try
End Function

Public Sub DrawDebugGraphicsLineList(ByVal list As List(Of LineSegment), ByVal color As Color)
	For Each lineSeg As LineSegment In list
		DrawDebuglineGraphics(lineSeg, color)
	Next
End Sub

Public Sub DrawDebugGraphicsList(ByVal list As Object)
	For Each obj As Object In list
		DrawDebugGraphics(obj)
	Next
End Sub

''' <summary>
''' Draws debug graphics
''' </summary>
''' <param name="obj"></param>
Public Sub DrawDebugGraphics(ByVal obj As Object)
	Dim graphicsNode As GraphicsNode = debuggingGraphics.AddNode(1)
	Dim lineGraphics As CurveGraphics = graphicsNode.AddCurveGraphics(obj)
End Sub

''' <summary>
''' Draws our transient line objects on-screen to aid debugging.
''' </summary>
''' <param name="lineSeg"></param>
Public Sub DrawDebuglineGraphics(ByVal lineSeg As LineSegment, ByVal lineColor As Color)
	Dim graphicsNode As GraphicsNode = debuggingGraphics.AddNode(1)
	Dim lineGraphics As CurveGraphics = graphicsNode.AddCurveGraphics(lineSeg)
	lineGraphics.Color = lineColor
End Sub


''' <summary>
''' Allows us to make "Is Equal To" tests ignoring the floating point problem whereby 
''' numbers that appear exact are actually different by a small margin.
''' </summary>
''' <param name="Value1"></param>
''' <param name="Value2"></param>
''' <param name="Tolerance"></param>
''' <returns></returns>
Public Function IsEqual(ByVal Value1 As Double, ByVal Value2 As Double, ByVal Optional Tolerance As Double = 1E-12) As Boolean
    Dim functionReturnValue As Boolean = False

    If Math.Abs(Value1 - Value2) < Tolerance Then
        functionReturnValue = True
    Else
        functionReturnValue = False
    End If

    Return functionReturnValue
End Function

''' <summary>
''' adds numbered annotations around sketchlines and points to aid automation
''' </summary>
''' <param name="SketchToDebug"></param>
Public Sub DebugSketchPointsEtc(ByVal SketchToDebug As PlanarSketch, ByVal ignoresketchlines As Boolean, Optional sketchpoints As List(Of SketchPoint) = Nothing)
	Dim objColl As ObjectCollection = transObjs.CreateObjectCollection()
	If Not ignoresketchlines Then
		For Each skline As SketchLine In SketchToDebug.SketchLines
			objColl.Add(skline)
		Next
		Call AnnotateSketchObjectsForDebug(SketchToDebug, objColl, 10) 'Sketch1.SketchLines)
		objColl.Clear()
	End If
	If sketchpoints Is Nothing Then
		For Each skPoint As SketchPoint In SketchToDebug.SketchPoints
			objColl.Add(skPoint)
		Next
	Else
		For Each skPoint As SketchPoint In sketchpoints
			objColl.Add(skPoint)
		Next	
	End If
	Call AnnotateSketchObjectsForDebug(SketchToDebug, objColl, 10) 'Sketch1.SketchPoints)
End Sub

''' <summary>
''' Creates a sketch based on a workplane
''' </summary>
''' <param name="compDef"></param>
''' <param name="plane"></param>
''' <returns></returns>
Public Function CreateSketch(ByVal compDef As ComponentDefinition, ByVal plane As WorkPlane) As PlanarSketch
	Dim newSketch As PlanarSketch = compDef.Sketches.Add(plane)
	Call CorrectForMissingOriginPoint(compDef, newSketch)
	If Not newSketch Is Nothing Then
		Return newSketch
	Else
		Return Nothing
	End If
End Function

''' <summary>
''' Checks if the supplied planarsketch has the part originpoint projected into it (if created by the API it won't!) and if not adds it.
''' </summary>
''' <param name="compDef"></param>
''' <param name="thisSketch"></param>
Public Sub CorrectForMissingOriginPoint(ByVal compDef As ComponentDefinition, ByRef thisSketch As PlanarSketch)
	Dim oOriginWP As WorkPoint  = compDef.WorkPoints.Item(1)
    'set as global above
'    Dim oOriginSketchPoint As SketchPoint
    For Each oSketchPoint As SketchPoint In thisSketch.SketchPoints
        If oSketchPoint.ReferencedEntity Is oOriginWP Then
            OriginSketchPoint = oSketchPoint
            Exit For
        End If
    Next
   
    ' Create the sketch point for the origin, if it doesn't already exist.
    If OriginSketchPoint Is Nothing Then
        ' Project the origin point onto the sketch.
        OriginSketchPoint = thisSketch.AddByProjectingEntity(compDef.WorkPoints.Item(1))
    End If
End Sub

''' <summary>
''' Adds/Returns the midpoint sketch point of any given line to the supplied sketchline object
''' </summary>
''' <param name="skLineToQuery"></param>
''' <returns></returns>
Public Function GetSketchLineMidPoint(ByVal skLineToQuery As SketchLine) As SketchPoint
	Dim parentSketch As PlanarSketch = skLineToQuery.parent
	Dim newpoint As Point2d = transGeom.CreatePoint2d(skLineToQuery.geometry.midpoint.x, skLineToQuery.geometry.midpoint.y)
	Dim lineMidPoint As SketchPoint = parentSketch.SketchPoints.Add(newpoint)
	Dim midpoint As GeometricConstraint = parentSketch.GeometricConstraints.AddMidpoint(lineMidPoint, skLineToQuery)
	Return lineMidPoint
End Function

''' <summary>
''' Not really necessary but still
''' </summary>
''' <param name="skLine"></param>
''' <returns></returns>
Public Function GetSketchLineMidPoint2d(ByVal skLine As SketchLine) As Point2d
	Return skLine.geometry.midpoint
End Function

''' <summary>
''' Places textboxes at the midpoint of any sketch line or sketchpoint for debugging purposes
''' </summary>
''' <param name="thisSketch"></param>
''' <param name="objcoll"></param>
''' <param name="textheight"></param>
Public Sub AnnotateSketchObjectsForDebug(ByVal thisSketch As PlanarSketch, ByVal objcoll As ObjectCollection, ByVal textheight As Double)
	Dim objInt As Integer = 1
	Dim formattedText As String = String.Empty
	MessageBox.Show(objcoll.count)
	For Each obj In objcoll
		If TypeOf obj Is SketchLine Then
			Dim skLine As SketchLine = obj
			Dim CenterPoint As Point2d = GetSketchLineMidPoint2d(skLine)
			AddFittedColouredSketchTextAtPoint(thisSketch, "black", CenterPoint, objInt.ToString(), textheight, VerticalTextAlignmentEnum.kAlignTextUpper, HorizontalTextAlignmentEnum.kAlignTextLeft)
			'start
			AddFittedColouredSketchTextAtPoint(thisSketch, "green", skLine.StartSketchPoint.Geometry, objInt.ToString(), textheight, VerticalTextAlignmentEnum.kAlignTextLower, HorizontalTextAlignmentEnum.kAlignTextLeft)
			'end
			AddFittedColouredSketchTextAtPoint(thisSketch, "orange", skLine.EndSketchPoint.Geometry, objInt.ToString(), textheight, VerticalTextAlignmentEnum.kAlignTextUpper, HorizontalTextAlignmentEnum.kAlignTextLeft)
			objInt += 1
		ElseIf TypeOf obj Is SketchPoint Then
			Dim skPoint As SketchPoint = obj
			AddFittedColouredSketchTextAtPoint(thisSketch, "red", skPoint.Geometry, objInt.ToString(), textheight, VerticalTextAlignmentEnum.kAlignTextLower, HorizontalTextAlignmentEnum.kAlignTextRight)
			objInt += 1
		End If
	Next
End Sub

''' <summary>
''' Adds a fitted, coloured piece of text at the given sketchpoint location
''' </summary>
''' <param name="sketchToEdit"></param>
''' <param name="textcolour"></param>
''' <param name="textpoint"></param>
''' <param name="textcontent"></param>
''' <param name="textHeight"></param>
''' <returns></returns>
Public Function AddFittedColouredSketchTextAtPoint(ByVal sketchToEdit As PlanarSketch, 
													ByVal textcolour As String, 
													ByVal textpoint As Point2d, 
													ByVal textcontent As String,
													ByVal textHeight As Double,
													ByVal Verticalalignment As VerticalTextAlignmentEnum,
													ByVal Horizontalalignment As HorizontalTextAlignmentEnum) As Inventor.TextBox
	Dim skTextBox As Inventor.TextBox = sketchToEdit.Textboxes.Addfitted(textpoint, textcontent)
	Dim tstart As Integer
	Dim tend As Integer
	Dim curtext As String = String.Empty
	Dim formattedText As String = String.Empty
	
	tstart = InStr(skTextBox.FormattedText, "'>") + 1
	If tstart <> 1 Then
	    tend = InStr(skTextBox.FormattedText, "</Style") - 1
	    curtext = Mid(skTextBox.FormattedText, tstart + 1, tend - tstart)
	Else
	    curtext = skTextBox.FormattedText  
	End If

	formattedText = "<StyleOverride FontSize='" & textHeight & "'>" & curtext & "</StyleOverride>"
	skTextBox.FormattedText = formattedText
	skTextBox.VerticalJustification = Verticalalignment
	skTextBox.HorizontalJustification = Horizontalalignment
	skTextBox.Color = GetColourFromString(textcolour)
	Return skTextBox
End Function

''' <summary>
''' Does what it says on the tin
''' </summary>
''' <param name="colourname"></param>
''' <returns></returns>
Public Function GetColourFromString(ByVal colourname As String) As Color
	colourname = colourname.ToLower()
	Select Case colourname
		Case "black"
			Return transObjs.CreateColor(255, 255, 255)
		Case "red"
			Return transObjs.CreateColor(255, 0, 0)
		Case "green"
			Return transObjs.CreateColor(0, 255, 0)
		Case "orange"
			Return transObjs.CreateColor(255, 165, 0)
		Case "blue"
			Return transObjs.CreateColor(0, 0, 255)
	End Select
End Function

''' <summary>
''' Allows us to query the parameters within the part file and get the latest-added
''' </summary>
''' <param name="compDef"></param>
''' <returns></returns>
Public Function GetLatestModelParameter(ByVal compDef As ComponentDefinition) As Parameter
	Dim ModelParamList As List(Of ModelParameter) = New List(Of ModelParameter)
	For Each MParameter As ModelParameter In compDef.Parameters.ModelParameters
		ModelParamList.Add(MParameter)	
	Next
	
	'debug
	'MessageBox.Show(ModelParamList.Count)
	Dim maxParam As Parameter = Nothing
	Dim maxParamNum As Integer = 0
	If ModelParamList.Count > 0 Then
		ModelParamList.Sort(Function(x As ModelParameter, y As ModelParameter) x.Name.CompareTo(y.Name))
		maxParam = (From param As ModelParameter In ModelParamList Select param).Last()
	End If
	If Not maxParam Is Nothing Then
		Return maxParam
	Else
		Return Nothing
	End If
End Function

Public Class PointsForSolidPlanes
	Public StartPoint As SketchPoint
	Public MidPoint As SketchPoint
	Public MidWorkPoint As WorkPoint
	Public EndPoint As SketchPoint
	Public startPointLines As List(Of LineSegment)
	Public EndPointLines As List(Of LineSegment)
	
	Public Sub [New](m_startPoint As SketchPoint,
                     m_midPoint As SketchPoint,
					 m_midWorkPoint As WorkPoint,
                     m_endPoint As SketchPoint,
					 m_startPointLines As List(Of LineSegment),
                     m_endPointLines As List(Of LineSegment))
        StartPoint = m_startPoint
        MidPoint = m_midPoint
		MidWorkPoint = m_midWorkPoint
        EndPoint = m_endPoint
		startPointLines = m_startPointLines
        EndPointLines = m_endPointLines
    End Sub
End Class

Public Class LineGroup
	Public parentLine As SketchLine
	Public startPointLines As List(Of LineSegment)
	Public EndPointLines As List(Of LineSegment)
	Public Sub [New](m_parentLine As SketchLine,
					 m_startPointLines As List(Of LineSegment),
                     m_endPointLines As List(Of LineSegment))
        parentLine = m_parentLine
        startPointLines = m_startPointLines
        EndPointLines = m_endPointLines
    End Sub
End Class
