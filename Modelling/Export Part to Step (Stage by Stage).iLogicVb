Imports System.Linq
Private Sub Main()
Call BeginExportFileStagesToStep
End Sub

'only works on Part files.
' portions of this code copied from: http://adndevblog.typepad.com/manufacturing/2012/06/getting-the-node-represented-in-the-inventor-part-browser-tree.html
Private Sub BeginExportFileStagesToStep()
	Dim oApp As Inventor.Application = ThisApplication
	Dim oPartDoc As Inventor.PartDocument = oApp.ActiveDocument
	EOPQuery = MsgBox("Would you like to export this part file to step format at each feature to look for translation errors?" _ 
		& vbCrLf & "Click 'Yes' to shrink." _ 
		& vbCrLf & "Click 'No' to expand" _ 
		, vbYesNo, "EOP Move and Step export")
	If EOPQuery = vbYes Then
		oPartDoc.ComponentDefinition.SetEndOfPartToTopOrBottom(True) ' Set to top
		Dim oPartDef As SheetMetalComponentDefinition = Nothing
		Dim oSheetMetalFeatures As SheetMetalFeatures = Nothing

		Dim TopNode As BrowserNode = Nothing
		
		If TypeOf oPartDoc.ComponentDefinition Is SheetMetalComponentDefinition Then
			oPartDef = oPartDoc.ComponentDefinition
			oSheetMetalFeatures = oPartDef.Features
			Break
			TopNode = oPartDoc.BrowserPanes("Model").TopNode
			TopNode = TopNode.BrowserNodes("Folded Model")

			If TopNode Is Nothing Then
				Throw New Exception("Unable to locate Folded Model Browser Node, exiting...")
			End If
		Else
			TopNode = oPartDoc.BrowserPanes("Model").TopNode
		End If
		
		For Each obrowsernode As BrowserNode In TopNode.BrowserNodes
			Break
			Logger.Debug(obrowsernode.BrowserNodeDefinition.Label)
			If Not obrowsernode.BrowserNodeDefinition.Label.Contains("View") And Not obrowsernode.BrowserNodeDefinition.Label.Contains("Origin") _
				And Not obrowsernode.BrowserNodeDefinition.Label.Contains("Table") And Not obrowsernode.BrowserNodeDefinition.Label.Contains("iMates") _
				And Not obrowsernode.BrowserNodeDefinition.Label.Contains("Bodies") And Not obrowsernode.BrowserNodeDefinition.Label.Contains("Blocks") Then
				Dim oNativeObject As Object = obrowsernode.BrowserNodeDefinition.NativeObject

				If TypeOf oNativeObject Is PartFeature Then
					Dim oFeature As PartFeature = oNativeObject
					oFeature.SetEndOfPart(False)

					ExportToStep(oFeature.Name)
				End If
			End If
		Next
	End If
End Sub

Private Sub ExportToStep(LastActiveFeatureName As String)
	' Get the STEP translator Add-In.
	Dim oSTEPTranslator As TranslatorAddIn
	oSTEPTranslator = ThisApplication.ApplicationAddIns.ItemById("{90AF7F40-0C01-11D5-8E83-0010B541CD80}")
	Dim oContext As TranslationContext
	oContext = ThisApplication.TransientObjects.CreateTranslationContext
	Dim oOptions As NameValueMap
	oOptions = ThisApplication.TransientObjects.CreateNameValueMap

	If oSTEPTranslator.HasSaveCopyAsOptions(ThisApplication.ActiveDocument, oContext, oOptions) Then
		' Set application protocol.
		' 2 = AP 203 - Configuration Controlled Design
		' 3 = AP 214 - Automotive Design
		oOptions.Value("ApplicationProtocolType") = 3
		' Other options...
		'oOptions.Value("Author") = ""
		'oOptions.Value("Authorization") = ""
		'oOptions.Value("Description") = ""
		'oOptions.Value("Organization") = ""
		oContext.Type = IOMechanismEnum.kFileBrowseIOMechanism
		Dim oData As DataMedium
		oData = ThisApplication.TransientObjects.CreateDataMedium
		oData.FileName = ThisDoc.PathAndFileName(False) & "_" & LastActiveFeatureName & "-exported.stp"
		oSTEPTranslator.SaveCopyAs(ThisApplication.ActiveDocument, oContext, oOptions, oData)
		OpenAndSaveExportedStep(oData.FileName)
	End If
End Sub

Private Sub OpenAndSaveExportedStep(FileToOpenAndSave as string)
	Dim PartDocToSave As PartDocument = ThisApplication.Documents.Open(FileToOpenAndSave)
	ThisApplication.CommandManager.ControlDefinitions.Item("AppZoomallCmd").Execute
	PartDocToSave.SaveAs(System.IO.Path.Combine(System.IO.Path.GetDirectoryName(FileToOpenAndSave), System.IO.Path.GetFileNameWithoutExtension(FileToOpenAndSave) & ".ipt"),False)
	PartDocToSave.Close()
end sub
