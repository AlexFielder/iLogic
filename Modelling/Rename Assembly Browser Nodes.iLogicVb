'credit goes to this thread: https://forums.autodesk.com/t5/inventor-customization/using-ilogic-to-rename-browser-nodes/m-p/4318636#M44814
' and PaulM for pointing me towards it.
Sub Main()
	'Grab the Assembly Document
	Dim oDoc As AssemblyDocument = ThisApplication.ActiveDocument
	Dim trans As Transaction = ThisApplication.TransactionManager.StartTransaction(oDoc, "Rename Browser Nodes to Description.")
	Try
		Dim oAsmCompDef As AssemblyComponentDefinition = oDoc.ComponentDefinition
		Dim oPane As BrowserPane = oDoc.BrowserPanes.Item("Model")
		For Each oOcc As ComponentOccurrence In oAsmCompDef.Occurrences
			If Not oOcc.IsSubstituteOccurrence Then
				Dim oCCDocument As Document = oOcc.Definition.Document
				If Not oCCDocument.FullFileName.Contains("Content Center") Then
					messagebox.show(oocc.name)
'					Dim invDesignInfo As PropertySet = oCCDocument.PropertySets.Item("Design Tracking Properties")
'					Dim invDescrProperty As Inventor.Property = invDesignInfo.Item("Description")
			        Dim summaryPropSet As Inventor.PropertySet = oCCDocument.PropertySets.Item("Inventor Summary Information")
        			Dim titleProp As Inventor.Property = summaryPropSet.Item("Title")
					Dim oSubAssyNode As BrowserNode = oPane.GetBrowserNodeFromObject(oOcc)
					If oSubAssyNode.NativeObject.Name.Contains(":") Then ' is likely one of multiple occurrences
						'messagebox.Show(oSubAssyNode.NativeObject.Name)
						Dim oldName As String = oSubAssyNode.NativeObject.Name
						Dim first As Integer = oldName.IndexOf(":")
						'MessageBox.Show("first= " & first)
						Dim last As Integer = oldName.LastIndexOf(":")
						'MessageBox.Show("last= " & last)
						Dim occNum As String = oldName.Substring(first, oldName.Length - last)
						'Messagebox.Show(occNum)
						If oldName <> titleProp.Value And Not titleProp.Value = String.Empty Then
							'Set The name 
							oSubAssyNode.NativeObject.Name = (titleProp.Value) & occNum
						End If
					Else
						If oSubAssyNode.NativeObject.Name <> titleProp.Value And Not titleProp.Value = String.Empty Then
						'Set The name 
						oSubAssyNode.NativeObject.Name = (titleProp.Value)
						End If
					End If
					
				End If
			End If
		Next
	trans.End()
	Catch Ex As Exception
		trans.Abort()
	End Try
End Sub
