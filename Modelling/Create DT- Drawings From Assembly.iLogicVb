Imports Inventor.ViewOrientationTypeEnum
Imports Inventor.DrawingViewStyleEnum
Imports System.IO

Public Sub Main

createDrawingsFromAssembly()
'CreateDrawingsFromAssembly(ThisDoc.Document)
End Sub

Public DefaultTemplate As String = "C:\Users\Public\Documents\Autodesk\Inventor 2018\Templates\standard.dwg" '<-- Put the path to your template here
Public ProjectRootFolder As String = String.Empty

Public Sub createDrawingsFromAssembly()
    ' Set reference to active document.
    ' This assumes the active document is an assembly
    Dim oDoc As Inventor.Document = ThisApplication.ActiveDocument
	ProjectRootFolder = System.IO.Path.GetDirectoryName(oDoc.FullFileName)
    Dim UseDefaultTemplate As DialogResult = MessageBox.Show("This is the path to the default template, do you wish to use this: " & vbCrLf & DefaultTemplate, "Use Default Template", MessageBoxButtons.YesNo)
	If UseDefaultTemplate = vbNo Then
		Dim oFileDlg As inventor.FileDialog = Nothing
		InventorVb.Application.CreateFileDialog(oFileDlg)
		oFileDlg.Filter = "Inventor DWG Template(*.dwg)|*.dwg|Inventor IDW Template(*.idw)|*.idw"
		oFileDlg.InitialDirectory = System.IO.Path.GetDirectoryName(ThisApplication.FileManager.GetTemplateFile(DocumentTypeEnum.kDrawingDocumentObject))
		oFileDlg.CancelError = True
		oFileDlg.MultiSelectEnabled = False
		dim openFileDialog as new OpenFileDialog()
		
		openFileDialog.InitialDirectory = System.IO.Path.GetDirectoryName(ThisApplication.FileManager.GetTemplateFile(DocumentTypeEnum.kDrawingDocumentObject))
		openFileDialog.Filter = "Inventor DWG Template(*.dwg)|*.dwg|Inventor IDW Template(*.idw)|*.idw"
		if openFileDialog.ShowDialog() = DialogResult.OK then
			Dim selectedfile1 as String = openFileDialog.FileName
			If selectedfile1 = String.Empty Then
				MessageBox.Show("You didn't pick a suitable file!" & vbCrLf & "I am going to exit now. Have a nice day!")
				Exit Sub
			Else
				DefaultTemplate = selectedfile1
			End If
		end if
	End If

	If TypeOf ThisApplication.ActiveDocument Is AssemblyDocument Then
		Dim oAssyDoc as AssemblyDocument = oDoc
		Dim oCompDef As Inventor.ComponentDefinition
		oCompDef = oAssyDoc.ComponentDefinition

    	For Each refDoc As Document In oAssyDoc.AllReferencedDocuments
			If refDoc.FullFileName.Contains("Content Center") Then Continue For
			BeginCreateDrawing(refDoc)
    	Next
	Else If TypeOf ThisApplication.ActiveDocument Is PartDocument Then
		Dim partDoc as PartDocument = oDoc
		BeginCreateDrawing(partDoc)
    End If
	MessageBox.Show("Done Creating Drawings!","You lucky thing you!")
End Sub

Private Sub BeginCreateDrawing(ByVal oDoc as Inventor.Document)
	Dim tmpfile As String = System.IO.Path.GetFileNameWithoutExtension(oDoc.FullFileName)
	Dim tmpDrawingName As String = projectRootFolder & "\Drgs\" & tmpfile & ".dwg"
	If Not projectRootFolder.Contains("Content Center Files") Then
    	If Not System.IO.File.Exists(tmpDrawingName) = True Then
			CreateDrawing(oDoc,tmpDrawingName)
		Else
			Dim tmpDrawDoc As DrawingDocument
			UpdateStatusBar("Opening existing drawing: " & tmpDrawingName) 
			tmpDrawDoc = ThisApplication.Documents.Open(tmpDrawingName, True)
		End If
	End If

End Sub
Private Sub CreateDrawing(ByVal oDoc as Inventor.Document,ByVal DrawingName As String)
	UpdateStatusBar(DrawingName) 
	Dim oBaseView As DrawingView
	Dim oView1 as DrawingView
	Dim oView2 as DrawingView
	Dim oView3 as DrawingView
	Dim oView4 as DrawingView 

	Dim ViewScale As Double = 1/10
	Dim NodeName() As String
	Dim InstNum As String

	'Define dwg Template File Location
	Dim oDrawingDoc As DrawingDocument = ThisApplication.Documents.Add(DocumentTypeEnum.kDrawingDocumentObject, TemplateFileName:= ThisApplication.FileManager.GetTemplateFile(DocumentTypeEnum.kDrawingDocumentObject), CreateVisible:= True)
	Dim oSheet As Sheet = oDrawingDoc.Sheets.Item(1)

	'Define 2d view bottom left corner points for four views
	oPoint1 = ThisApplication.TransientGeometry.CreatePoint2d(11, 11) 'BASE
	oPoint2 = ThisApplication.TransientGeometry.CreatePoint2d(28, 11) 'RIGHT
	oPoint3 = ThisApplication.TransientGeometry.CreatePoint2d(11, 20) 'TOP
	oPoint4 = ThisApplication.TransientGeometry.CreatePoint2d(28, 20) 'ISOMETRIC
	'ISOMETRIC?
	'view styles can be: 
	'DrawingViewStyleEnum.kHiddenLineRemovedDrawingViewStyle
	'DrawingViewStyleEnum.kHiddenLineDrawingViewStyle
	'DrawingViewStyleEnum.kShadedDrawingViewStyle
	'DrawingViewStyleEnum.kShadedHiddenLineDrawingViewStyle
	'DrawingViewStyleEnum.kFromBaseDrawingViewStyle
	'
	
	oBaseView = oSheet.DrawingViews.AddBaseView(oDoc,oPoint1, ViewScale,kFrontViewOrientation, DrawingViewStyleEnum.kHiddenLineRemovedDrawingViewStyle)', KTANGENTEDGESON)

	oView2 = oSheet.DrawingViews.AddProjectedView(oBaseView,oPoint2, DrawingViewStyleEnum.kFromBaseDrawingViewStyle)
	oView3 = oSheet.DrawingViews.AddProjectedView(oBaseView,oPoint3, DrawingViewStyleEnum.kFromBaseDrawingViewStyle)
	oView4 = oSheet.DrawingViews.AddProjectedView(oBaseView,oPoint4, DrawingViewStyleEnum.kFromBaseDrawingViewStyle)
	oDrawingDoc.SaveAs(DrawingName,False)
	oDrawingDoc.Close(True)
	'synchronize drawing properties to the model it's based upon:
	'these next lines don't work because the code needs to be run from the drawing itself!
	'iLogicVb.RunExternalRule("C:\VAULT WORKING FOLDER\Designs\Synchronize iProperties between parts and drawings.iLogicVb")
	'oDrawingDoc.Save()
End Sub

''' <summary>
''' updates the statusbar with a string value.
''' </summary>
''' <param name="Message"></param>
''' <remarks></remarks>
Private Sub UpdateStatusBar(ByVal Message As String)
	ThisApplication.StatusBarText = Message
End Sub

''' <summary>
''' Updates the statusbar with a percentage value
''' </summary>
''' <param name="percent"></param>
''' <param name="Message"></param>
''' <remarks></remarks>
Private Sub UpdateStatusBar(ByVal percent As Double, ByVal Message As String)
	ThisApplication.StatusBarText = Message + " (" + percent.ToString("P1") + ")"
End Sub
