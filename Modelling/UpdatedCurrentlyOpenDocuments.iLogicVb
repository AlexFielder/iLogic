Sub Main()
    'FOR SAPPHIRE ONLY CURRENTLY!
    'should hopefully perform an update on each open assembly file skeleton base part
    For Each oDoc In ThisApplication.Documents
        If oDoc.DocumentType = Inventor.DocumentTypeEnum.kAssemblyDocumentObject Then 'And Not oDoc.FullFilename.Contains("Panel") Then
            'MessageBox.Show(odoc.fullfilename,"Parent Assembly file")
'            Dim AssemblyRootFolder As String = System.IO.Path.GetDirectoryName(oDoc.FullFileName)
'            Dim PartFileNameToOpen As String = System.IO.Path.GetFileNameWithoutExtension(oDoc.FullFileName)
'            Dim filepathtoopen As String = AssemblyRootFolder & "\" & PartFileNameToOpen & ".ipt"
'            'MessageBox.Show(filepathtoopen, "Title")
'            Dim partToUpdate As PartDocument = ThisApplication.Documents.Open(filepathtoopen, True)
'            partToUpdate.Activate
'            'this is the one that actually forces the update!
'            partToUpdate.Rebuild2(True)
'            partToUpdate.Update2(True)
'            InventorVb.DocumentUpdate()
'            partToUpdate.Save()
'            partToUpdate.Close
			Dim AssyDoc As AssemblyDocument = oDoc
            AssyDoc.Rebuild2(True)
            AssyDoc.Update2(True)
            AssyDoc.Save()
			AssyDoc.Close()
        End If
    Next

End Sub
