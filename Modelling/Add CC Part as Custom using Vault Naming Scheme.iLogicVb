Option Explicit On
AddReference "Autodesk.Connectivity.WebServices"
AddReference "Autodesk.DataManagement.Client.Framework.Forms"
AddReference "Autodesk.DataManagement.Client.Framework.Vault"
AddReference "Autodesk.DataManagement.Client.Framework.Vault.Forms"

Imports ACW = Autodesk.Connectivity.WebServices
Imports VDF = Autodesk.DataManagement.Client.Framework
Imports Autodesk.DataManagement.Client.Framework.Vault.Services
Imports Autodesk.DataManagement.Client.Framework.Vault.Currency.Connections
'''
''' Copied from this thread: https://forums.autodesk.com/t5/vault-customization/vault-login-vb-net/m-p/7735557#M5944

Public Sub Main()
Call PlaceComponent("BS 4168 : Part 1 Hexagon Socket Head Cap Screw - Metric", "Fasteners", "Bolts", "Socket Head", "M8", "30", "Grade A4")
End Sub

Public Connection As VDF.Vault.Currency.Connections.Connection = Nothing
Public SchemeName As String = "TestScheme"

''' <summary>
''' Allows the user to place a component from the Content Centre
''' based on supplied variables and names the resultant occurence using the required
''' Vault naming scheme
''' </summary>
''' <param name="FamilyToPlace"></param>
''' <param name="CCCategory"></param>
''' <param name="SubCategory"></param>
''' <param name="SubSubCategory"></param>
''' <param name="SizeOne"></param>
''' <param name="SizeTwo"></param>
Public Sub PlaceComponent(ByVal FamilyToPlace As String, 
							ByVal CCCategory As String, 
							ByVal SubCategory As String, 
							ByVal SubSubCategory As String, 
							ByVal SizeOne As String, 
							ByVal SizeTwo As String, 
							ByVal RequiredMaterial As String)
	If Not TypeOf (ThisApplication.ActiveDocument.ComponentDefinition) Is AssemblyComponentDefinition Then
		MessageBox.Show("Not an assembly!")
		Exit Sub
	End If
	Dim oAssCompDef As AssemblyComponentDefinition = ThisApplication.ActiveDocument.ComponentDefinition

	Dim oTransG As TransientGeometry = ThisApplication.TransientGeometry

	Dim oMatrix As Matrix = oTransG.CreateMatrix 

	Dim oOcc As ComponentOccurrence

	Dim hexHeadNode As ContentTreeViewNode = ThisApplication.ContentCenter.TreeViewTopNode.ChildNodes.Item(CCCategory).ChildNodes.Item(SubCategory).ChildNodes.Item(SubSubCategory)

	Dim oFam As ContentFamily = (From checkFamily As ContentFamily In hexHeadNode.Families
								Where checkFamily.DisplayName = FamilyToPlace
								Select checkFamily).FirstOrDefault()
	If Not oFam is Nothing Then
		'I get the ContentFamily <oFam> depending on <Norm> and <Material>
		Logger.Debug(CCCategory & " | " & SubCategory & " | " & SubSubCategory)
		logTableRows(oFam)
		Dim oTR As ContentTableRow = Nothing
		If CCCategory = "Fasteners" Then
			Logger.Debug("Working with the Bolts category")
			Dim sizeString As String = SizeOne & " x " & SizeTwo
			Dim sizeCol As ContentTableColumn = oFam.TableColumns("SIZE")
			Dim materialCol As ContentTableColumn = oFam.TableColumns("MATERIAL_ALIAS")
			oTR = (From Row As ContentTableRow In oFam.TableRows
					Where Row.GetCellValue(sizeCol) = sizeString And Row.GetCellValue(materialCol)= RequiredMaterial
					Select row).FirstOrDefault()
		Else If CCCategory = "Structural Shapes" Then
				
		Else If CCCategory = "" Then
				
		End If
		'I get the ContentTableRow <oTR> depending on a user preselected value 
		If Not oTR Is Nothing Then
			Dim oIntName As String = oTR.InternalName
			Dim oFailReas As MemberManagerErrorsEnum
			Dim oFailMess As String
			Dim oMemFileName As String
			Dim oValues As NameValueMap = ThisApplication.TransientObjects.CreateNameValueMap
			Dim TestValue As String = "LOREM IPSUM DOLOR"
			oValues.Add("B_L", TestValue) 'this is an company internal value; it is an numeric parameter

			oMatrix.SetTranslation(oTransG.CreateVector(0, 0, 0))
			'oMemFileName = oFam.CreateMember(oIntName, oFailReas, oFailMess, , , , oValues)
			logger.Debug("looks like we got a row to work with")
			Dim oFileName As String = getFilenameFromVaultNamingScheme(SchemeName, oIntName)
			oMemFileName = oFam.CreateMember(oIntName, oFailReas, oFailMess,ContentMemberRefreshEnum.kRefreshOutOfDateParts, True, oFileName, oValues)
			oOcc = oAssCompDef.Occurrences.Add(oMemFileName, oMatrix)
			oOcc.Grounded = True
		Else
			Logger.Error("Something went awry when getting the ContentTableRow from CC!")
		End If
	Else
		Logger.Error("Something went awry when getting the family from CC!")
	End If
End Sub

''' <summary>
''' Gets the filename from the Vault Naming Scheme
''' </summary>
''' <param name="RequiredSchemeString"></param>
''' <returns></returns>
Public Function getFilenameFromVaultNamingScheme(RequiredSchemeName As String, RequiredSchemeString As String) As String
	'uses Windows Authentication:
	Dim results As VDF.Vault.Results.LogInResult = VDF.Vault.Library.ConnectionManager.LogIn("localhost", "Vault", "", "", AuthenticationFlags.WindowsAuthentication, Nothing)
	Connection = results.Connection
	Dim genNum As String = String.Empty
	If Not Connection Is Nothing Then
		Dim numSchemes As ACW.NumSchm() = Connection.WebServiceManager.DocumentService.GetNumberingSchemesByType(Autodesk.Connectivity.WebServices.NumSchmType.Activated)
		Dim requiredScheme As ACW.NumSchm = (From sch As ACW.NumSchm In numSchemes
											Where sch.Name = RequiredSchemeName
											Select sch).FirstOrDefault()
		Dim numGenArgs() As String = {RequiredSchemeString}
	'	numGenArgs += 
		genNum = Connection.WebServiceManager.DocumentService.GenerateFileNumber(requiredScheme.SchmID, numGenArgs)
	Else
		Logger.Error("Vault didn't work!")			
	End If
	Return genNum + RequiredSchemeString
End Function

Public Sub logTableRows(ByVal CCFamily As ContentFamily)
	For Each col As ContentTableColumn In CCFamily.TableColumns
		Logger.Debug(col.InternalName)
	Next
End Sub
