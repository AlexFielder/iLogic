Option Explicit On
'the point of this class is to enable us to promote Appearance overrides 
'into useful parameters that we might pull onto a drawing
'
'It is based in part on this:
' https://github.com/ADN-DevTech/Inventor-Training-Material/blob/master/Module%2013%20-%20Part%20Advanced/Inv2014_New_API_Demo/Inv2014_New_API_Demo/Form1.vb#L626
Public Sub Main()
If TypeOf ThisApplication.ActiveDocument Is PartDocument Then
	'work on the part itself
	PromotePartOverridesToUserParameters(ThisApplication.ACtiveDocument)
ElseIf TypeOf ThisApplication.ActiveDocument Is AssemblyDocument Then
	Dim AsmDef as AssemblyComponentDefinition = ThisApplication.ActiveDocument.ComponentDefinition
	'work on occurrences
	For Each occ in asmDef.Occurrences
		If occ.DefinitionDocumentType = DocumentTypeEnum.kPartDocumentObject Then
			Dim tmpPart As partDocument = occ.definition.Document
			PromotePartOverridesToUserParameters(tmpPart)
		Else
			Throw New notimplementedException
		End If
	Next
End If
End Sub

Public Sub PromotePartOverridesToUserParameters(ByVal partDoc as PartDocument)
	Dim transObjs As TransientObjects = ThisApplication.TransientObjects
    Dim overridesColl As ObjectCollection = transObjs.CreateObjectCollection()
    If Not partDoc.ComponentDefinition.AppearanceOverridesObjects Is Nothing Then
        Dim obj As Object
        For Each obj In partDoc.ComponentDefinition.AppearanceOverridesObjects
            If TypeOf obj Is SurfaceBody Then
                '            objcoll.add AppearanceSourceTypeEnum.kPartAppearance
            ElseIf TypeOf obj Is PartFeature Then
                '            obj.AppearanceSourceType = AppearanceSourceTypeEnum.kBodyAppearance
            ElseIf TypeOf obj Is Face Then
                Dim thisFace As Face = obj
                overridesColl.Add(thisFace.Appearance.DisplayName)
            Else
                MsgBox("Unexpected type with appearance override: " & TypeName(obj))
            End If
        Next
        'Dim PartDocName As String = System.IO.Path.GetFileNameWithoutExtension(partDoc.DisplayName) & ":1"
        'commented because API > iLogic
        'Dim oParams As Parameters = partDoc.ComponentDefinition.Parameters
        Dim ParamInt As Integer = 1
        If overridesColl.Count > 0 Then
            For Each overrideName As String In overridesColl
                Dim customParamName As String = "Appearance00" & ParamInt.ToString
                Try
					Parameter(customParamName) = overrideName
                Catch 'catch the error if the parameter doesn't already exist
					Dim oParameters As Inventor.Parameters = partDoc.ComponentDefinition.Parameters
					'because this is text the following will work:
					oParameters.UserParameters.AddByValue(customParamName, overrideName, UnitsTypeEnum.kTextUnits)
                End Try
                ParamInt += 1
            Next
        End If
    Else
        MessageBox.Show("No Overrides found!")
    End If
    overridesColl = Nothing
    transObjs = Nothing
End Sub
