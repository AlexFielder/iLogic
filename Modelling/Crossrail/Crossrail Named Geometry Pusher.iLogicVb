Option Explicit On

Imports System.Linq
Imports System.Collections.Generic

Sub Main()
	Dim AssyDoc As AssemblyDocument = ThisApplication.ActiveDocument
	Dim AssyDef As AssemblyComponentDefinition = AssyDoc.ComponentDefinition
	
	Dim CompOccs As ComponentOccurrences = AssyDef.Occurrences
	DerivedCompList = (From tmpDoc As Document In AssyDoc.AllReferencedDocuments
						Where TypeOf tmpDoc Is PartDocument
						Let partDoc As PartDocument = tmpDoc
						Let partDef As PartComponentDefinition = partDoc.ComponentDefinition
						Where Not partDef.ReferenceComponents.DerivedPartComponents Is Nothing
						Where Not partDef.ReferenceComponents.DerivedPartComponents.Count = 0
						Let derivedPartComp As DerivedPartComponent = partDef.ReferenceComponents.DerivedPartComponents(1)
						Select derivedPartComp).ToList()
	If DerivedCompList.Count > 0 Then
		MessageBox.Show("Count of derived components = " & DerivedCompList.Count)

		For Each derivedPartComp As DerivedPartComponent In DerivedCompList
			Dim tmpDef As DerivedPartDefinition = derivedPartComp.Definition
			Dim tmpDoc As PartDocument = derivedPartComp.ReferencedDocumentDescriptor.ReferencedDocument
			Dim listofObjectsToPush As List(Of Object) = New List(Of Object)
			listofObjectsToPush.AddRange(GetNamedGeometry(tmpDoc, "*"))
			If listofObjectsToPush.Count > 0 Then
				PushNamedGeometryToDerivedParts(AssyDoc, listofObjectsToPush)
			Else
				MessageBox.Show("No Named Geometry found to push in: " & derivedPartComp.Name)
			End If
		Next
		
		'Attempting to get the named geometry from the derived part file in each component.
	'	Dim objColl As ObjectCollection = ThisApplication.TransientObjects.CreateObjectCollection
	'	Dim DerivedColl As ObjectCollection = ThisApplication.TransientObjects.CreateObjectCollection
	End If
	
	
End Sub

Public DerivedCompList As List(Of DerivedPartComponent) = New List(Of DerivedPartComponent)

Public Sub PushNamedGeometryToDerivedParts(AssyDoc As AssemblyDocument, listToPush As List(Of Object))
	
	For Each derivedComp As DerivedPartComponent In DerivedCompList
		'Dim referencedDoc As Document = derivedComp.ReferencedDocumentDescriptor.ReferencedDocument
		'this next line needs to get the derived document from the allreferenceddocuments collection otherwise we're just checking the original Multi-Body Part file again.
		Dim defToEdit As DerivedPartDefinition = derivedComp.Definition
		'this works but gets the parent MBPart file instead!
'		Dim docToEdit As PartDocument = (From doc As Document In AssyDoc.AllReferencedDocuments
'										Where TypeOf doc Is PartDocument
'										Let partDoc As PartDocument = doc
'										Where partDoc Is derivedComp.ReferencedDocumentDescriptor.ReferencedDocument
'										Select partDoc).FirstOrDefault()
'		If Not docToEdit Is Nothing Then
			'check for and add if not existing the iLogicEntityNameSet attributeset
'			Dim iLogicAttSet As AttributeSet = docToEdit.AttributeSets("")
Break
'these lines don't do anything because there aren't any attributesets in the derived component at this stage!
'			If Not derivedComp.AttributeSets.Count = 0 Then
'				Dim existingAttSets As Boolean = derivedComp.AttributeSets.NameIsUsed("iLogicEntityNameSet")
'				If existingAttSets Then
'					Break
'					Dim attribSetsEnum As AttributeSetsEnumerator = derivedComp.AttributeSets("iLogicEntityNameSet") 'docToEdit.AttributeManager.FindAttributeSets("iLogicEntityNameSet")
'					If Not attribSetsEnum Is Nothing Then
'						For Each attset As AttributeSet In attribSetsEnum
'							attset.Delete()
'						Next
'					End If
'				End If
'			End If
Break
			Dim docToEdit As PartDocument = derivedComp.Parent.Document 'derivedComp.ReferencedDocumentDescriptor.ReferencedDocument
			Dim surfacebodyToEdit As SurfaceBody = docToEdit.ComponentDefinition.SurfaceBodies.Item(1)
			'Dim surfacebodyToEdit As SurfaceBody = derivedComp.SurfaceBodies.Item(1)
			Break
			If Not surfacebodyToEdit Is Nothing Then
				'Split the listToPush into faces or edges lists
				Dim edgesToEditList As List(Of Edge) = (From x As Object In listToPush
														Where TypeOf x Is Edge
														Let thisEdge As Edge = x
														Select thisEdge).ToList() 'listToPush.Where(Function(x As Object) TypeOf x Is Edge).Tolist(Of Edge)
				Dim facesToEditList As List(Of Face) = (From x As Object In listToPush
														Where TypeOf x Is Face
														Let thisFace As Face = x
														Select thisFace).ToList() 'listToPush.Where(Function(x As Object) TypeOf x Is Face).Tolist(Of Face)
				Break
				'Edges
				For Each edgeToCheck As Edge In surfacebodyToEdit.Edges
'					Dim edgeToEdit As Edge = edgesToEditList.Find(Function(matchEdge As Edge) matchEdge.TransientKey = edgeToCheck.TransientKey)
					Dim matchedPair As MatchingGeom = (From matchEdge As Edge In edgesToEditList
														Where matchEdge.TransientKey = edgeToCheck.TransientKey
														Select New MatchingGeom With {
															.CheckObj = edgeToCheck,
															.MatchingObj = matchEdge }).FirstOrDefault()
Break
					Dim edgeToEdit As Edge = matchedPair.MatchingObj
					If Not edgeToEdit Is Nothing Then
						Dim iLogicEntityName As String = GetAttributeValueFromObject(matchedPair.CheckObj, "iLogicEntityNameSet", "default")
						If Not iLogicEntityName = String.Empty Then
							MessageBox.Show("iLogicEntityName" = iLogicEntityName)
							Dim newAttSet As AttributeSet = edgeToEdit.AttributeSets.Add("iLogicEntityNameSet")
							Dim edgeAtt As Attribute = newAttSet.Add("iLogicEntityName", ValueTypeEnum.kStringType, iLogicEntityName)
						End If
						Break
					End If
				Next
				'Faces
				For Each faceTocheck As Face In surfacebodyToEdit.Faces
					Dim matchedPair As MatchingGeom = (From matchface As Face In facesToEditList
														Where matchface.TransientKey = faceToCheck.TransientKey
														Select New MatchingGeom With {
															.CheckObj = faceToCheck,
															.MatchingObj = matchface }).FirstOrDefault()
Break
					Dim faceToEdit As Face = matchedPair.MatchingObj
					If Not faceToEdit Is Nothing Then
						Dim iLogicEntityName As String = GetAttributeValueFromObject(matchedPair.CheckObj, "iLogicEntityNameSet", "default")
						If Not iLogicEntityName = String.Empty Then
							MessageBox.Show("iLogicEntityName" = iLogicEntityName)
							Dim newAttSet As AttributeSet = faceToEdit.AttributeSets.Add("iLogicEntityNameSet")
							Dim faceAtt As Attribute = newAttSet.Add("iLogicEntityName", ValueTypeEnum.kStringType, iLogicEntityName)
						End If
						Break
					End If
				Next
			End If
			'need to add the iLogicEntityNameSet to the document so iLogic picks it up.
			docToEdit.AttributeSets.Add("iLogicEntityNameSet")
			Dim attribSetEnum As AttributeSetsEnumerator = docToEdit.AttributeManager.FindAttributeSets("iLogicEntityNameSet*")
			
'		Else
'			messagebox.Show("Something broke!")
'		End If
	Next
'	For Each obj As Object In listToPush
		
'	Next
End Sub

''' <summary>
''' Gets a named attribute from an object
''' </summary>
''' <param name="attributedObject"></param>
''' <param name="attSetName"></param>
''' <param name="attName"></param>
''' <returns></returns>
Function GetAttributeValueFromObject(ByVal attributedObject As Object, ByVal attSetName As String, ByVal attName As String) As String
    Dim existingAttSet As AttributeSet = attributedObject.AttributeSets(attSetName)
	Dim value As String = String.Empty
	If attName = "default" Then
		value = (From oAtt In existingAttSet Select oAtt).FirstOrDefault().Value
	Else
    	value = (From oAtt In existingAttSet Where oAtt.Name = attName Select oAtt).FirstOrDefault().Value
	End If
    If value IsNot Nothing Then
        Return value
    Else
        Return String.Empty
    End If
End Function

''' <summary>
''' This method copied from here:
''' https://forums.autodesk.com/t5/inventor-customization/vb-net-find-face-by-face-name/m-p/7950234/highlight/true#M83557
''' </summary>
Public Sub GetNameTest()
    Dim doc As PartDocument = ThisApplication.ActiveDocument
    Dim faceOrEdge As Object = GetNamedEntity(doc, "Brian")
End Sub

''' <summary>
''' Returns a list of objects from the supplied document
''' </summary>
''' <param name="doc"></param>
''' <param name="name"></param>
''' <returns></returns>
Public Function GetNamedGeometry(doc As Document, name As String) As List(Of Object)
	Dim listofNamedGeom As List(Of Object) = New List(Of Object)
	Dim attribMgr As AttributeManager = doc.AttributeManager
    Dim objsFound As ObjectCollection = ThisApplication.TransientObjects.CreateObjectCollection
    objsFound = attribMgr.FindObjects("iLogicEntityNameSet", "iLogicEntityName", name)
	If Not objsFound.Count = 0 Then
		'debug
		MessageBox.Show("Count of items found in iLogicEntityNameSet = " & objsFound.Count)
		For i = 1 To objsFound.Count
			listofNamedGeom.Add(objsFound.Item(i))		
		Next i
	End If
	
	If listofNamedGeom.Count > 0 Then
		Return listofNamedGeom
	Else
		Return Nothing
	End If
End Function

''' <summary>
''' This method copied from here:
''' https://forums.autodesk.com/t5/inventor-customization/vb-net-find-face-by-face-name/m-p/7950234/highlight/true#M83557
''' </summary>
''' <param name="doc">Document to search</param>
''' <param name="name">Object To look for</param>
''' <returns></returns>
Public Function GetNamedEntity(doc As Inventor.Document, name As String) As Object
    Dim attribMgr As AttributeManager = doc.AttributeManager
    Dim objsFound As ObjectCollection
    objsFound = attribMgr.FindObjects("iLogicEntityNameSet", "iLogicEntityName", name)
    'debug
	MessageBox.Show("Count of items found in iLogicEntityNameSet = " & objsFound.Count)
    If objsFound.Count > 0 Then
        Return(objsFound.Item(1))
    Else
        Return(Nothing)
    End If
End Function

Public Class MatchingGeom
	Public CheckObj As Object
	Public MatchingObj As Object
End Class
