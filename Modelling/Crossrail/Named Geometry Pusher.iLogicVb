Option Explicit On

Imports System.Linq
Imports System.Collections.Generic

Sub Main()
	Dim AssyDoc As AssemblyDocument = ThisApplication.ActiveDocument
	Dim AssyDef As AssemblyComponentDefinition = AssyDoc.ComponentDefinition
	
	Dim CompOccs As ComponentOccurrences = AssyDef.Occurrences
	DerivedCompList = (From tmpDoc As Document In AssyDoc.AllReferencedDocuments
						Where TypeOf tmpDoc Is PartDocument
						Let partDoc As PartDocument = tmpDoc
						Let partDef As PartComponentDefinition = partDoc.ComponentDefinition
						Where Not partDef.ReferenceComponents.DerivedPartComponents Is Nothing
						Where Not partDef.ReferenceComponents.DerivedPartComponents.Count = 0
						Let derivedPartComp As DerivedPartComponent = partDef.ReferenceComponents.DerivedPartComponents(1)
						Select derivedPartComp).ToList()
	If DerivedCompList.Count > 0 Then
'		MessageBox.Show("Count of derived components = " & DerivedCompList.Count)
		For Each derivedPartComp As DerivedPartComponent In DerivedCompList
			Dim tmpDef As DerivedPartDefinition = derivedPartComp.Definition
			Dim tmpDoc As PartDocument = derivedPartComp.ReferencedDocumentDescriptor.ReferencedDocument
			Dim listofObjectsToPush As List(Of MatchingGeom) = New List(Of MatchingGeom)
			listofObjectsToPush.AddRange(GetNamedGeometry(tmpDoc, "*"))
			If listofObjectsToPush.Count > 0 Then
'				MessageBox.Show("Count of items in the multi-body part file: " & listofObjectsToPush.Count)
				PushNamedGeometryToDerivedParts(AssyDoc, listofObjectsToPush)
			Else
				MessageBox.Show("No Named Geometry found to push in: " & derivedPartComp.Name)
			End If
		Next
	End If
	
	
End Sub

Public DerivedCompList As List(Of DerivedPartComponent) = New List(Of DerivedPartComponent)

Public Sub PushNamedGeometryToDerivedParts(AssyDoc As AssemblyDocument, listToPush As List(Of MatchingGeom))
	
	For Each derivedComp As DerivedPartComponent In DerivedCompList
		Dim defToEdit As DerivedPartDefinition = derivedComp.Definition
		Dim parentPartDoc As PartDocument = derivedComp.Parent.Document
		Dim parentPartDef As PartComponentDefinition = parentPartDoc.ComponentDefinition
		Dim parentPartSurfaceBodies As SurfaceBodies = parentPartDef.SurfaceBodies
		Dim parentSurfaceBody As SurfaceBody
		Dim surfaceReferenceFeature As ReferenceFeature = derivedComp.SolidBodies.Item(1)
		Dim surfacebodyToEdit As SurfaceBody = surfaceReferenceFeature.SurfaceBodies.Item(1)
		parentSurfaceBody = surfaceReferenceFeature.ReferencedEntity
		If Not surfacebodyToEdit Is Nothing Then
			Dim edgesToCopyList As List(Of MatchingGeom) = (From x As MatchingGeom In listToPush
													Where TypeOf x.CheckObj Is Edge
													Select x).ToList()
			Dim facesToCopyList As List(Of MatchingGeom) = (From x As MatchingGeom In listToPush
													Where TypeOf x.CheckObj Is Face
													Select x).ToList()
														
			Dim matchedEdgePairList As List(Of MatchingGeom) = New List(Of MatchingGeom)
			Dim matchingEdgeResult As List(Of MatchingGeom) = New List(Of MatchingGeom)
			matchedEdgePairList = GetListOfMatchingEdges(parentSurfaceBody.Edges, surfacebodyToEdit.Edges)

			'Edges

			If Not matchedEdgePairList Is Nothing Then
				For Each matchedEdge As MatchingGeom In matchedEdgePairList
					For Each edgeToCopy As MatchingGeom In edgesToCopyList
						If (matchedEdge.CheckObj Is edgeToCopy.CheckObj) Then
							matchingEdgeResult.Add(New MatchingGeom With {.CheckObj = matchedEdge.CheckObj, .MatchingObj = matchedEdge.MatchingObj})
						End If
					Next
				Next

				If matchingEdgeResult.Count > 0 Then
					For Each matchedPair As MatchingGeom In matchingEdgeResult
						Dim edgeToEdit As Edge = matchedPair.MatchingObj
						Dim iLogicEntityName As String = GetAttributeValueFromObject(matchedPair.CheckObj, "iLogicEntityNameSet", "default")
						If Not iLogicEntityName = String.Empty Then
							Logger.Debug("Adding iLogicEntityName = " & iLogicEntityName & " to " & derivedComp.Name)
							'MessageBox.Show("iLogicEntityName = " & iLogicEntityName)
							Dim newAttSet As AttributeSet = edgeToEdit.AttributeSets.Add("iLogicEntityNameSet")
							Dim edgeAtt As Attribute = newAttSet.Add("iLogicEntityName", ValueTypeEnum.kStringType, iLogicEntityName)
						End If
					Next
				End If
			End If
			
			'Faces
			For Each faceTocheck As Face In surfacebodyToEdit.Faces
				Dim matchedPair As MatchingGeom = (From matchface As Face In facesToCopyList
													Where matchface Is faceTocheck
													Select New MatchingGeom With {
														.CheckObj = faceTocheck,
														.MatchingObj = matchface }).FirstOrDefault()
'Break
				If Not matchedPair Is Nothing Then
					Dim faceToEdit As Face = matchedPair.MatchingObj
'Break
					Dim iLogicEntityName As String = GetAttributeValueFromObject(matchedPair.CheckObj, "iLogicEntityNameSet", "default")
					If Not iLogicEntityName = String.Empty Then
						MessageBox.Show("iLogicEntityName" = iLogicEntityName)
						Dim newAttSet As AttributeSet = faceToEdit.AttributeSets.Add("iLogicEntityNameSet")
						Dim faceAtt As Attribute = newAttSet.Add("iLogicEntityName", ValueTypeEnum.kStringType, iLogicEntityName)
					End If
					Break
				End If
			Next
		End If
	Next
End Sub

''' <summary>
''' initial concept copied from here: https://adndevblog.typepad.com/manufacturing/2014/11/get-edge-in-derived-part-that-drives-work-point.html
''' </summary>
''' <param name="edgesToCheck"></param>
''' <param name="bodyEdges"></param>
''' <returns></returns>
Function GetListOfMatchingEdges(edgesToCheck As Edges, bodyEdges As Edges) As List(Of MatchingGeom)
	Dim combinedList As List(Of MatchingGeom) = New List(Of MatchingGeom)
	For Each e2 As Edge In bodyEdges
		For Each e As Edge In edgesToCheck
			If (e2.Faces.Count = 2 And E.faces.count = 2) Then 'because we have a split loft which means there's one edge with only 1 face adjacent to it!?
				If (e2.Faces(1).ReferencedEntity Is E.Faces(1) And _
			        e2.Faces(2).ReferencedEntity Is E.Faces(2)) Or _
			       (e2.Faces(1).ReferencedEntity Is E.Faces(2) And _
			        e2.Faces(2).ReferencedEntity Is E.Faces(1)) Then
			      	combinedList.Add(New MatchingGeom With {.CheckObj = E, .MatchingObj = e2})
			    End If
			End If
		Next
	Next
	If Not combinedList.Count = 0 Then
		Return combinedList
	Else
		Return Nothing
	End If
End Function

''' <summary>
''' Copied from this post: https://adndevblog.typepad.com/manufacturing/2014/11/get-edge-in-derived-part-that-drives-work-point.html
''' </summary>
''' <param name="E"></param>
''' <param name="sb"></param>
Function GetEdgeInSurfaceBody(e As Edge, sb As SurfaceBody) As Edge
  ' Go through the edges inside the iPart instance
  ' to see which one connects the same faces
  Dim e2 As Edge
  For Each e2 In sb.Edges
    If (e2.Faces(1).ReferencedEntity Is e.Faces(1) And _
        e2.Faces(2).ReferencedEntity Is e.Faces(2)) Or _
       (e2.Faces(1).ReferencedEntity Is e.Faces(2) And _
        e2.Faces(2).ReferencedEntity Is e.Faces(1)) Then
      Return e2
      Exit Function
    End If
  Next
End Function

''' <summary>
''' Gets a named attribute from an object
''' </summary>
''' <param name="attributedObject"></param>
''' <param name="attSetName"></param>
''' <param name="attName"></param>
''' <returns></returns>
Function GetAttributeValueFromObject(ByVal attributedObject As Object, ByVal attSetName As String, ByVal attName As String) As String
    Dim existingAttSet As AttributeSet = attributedObject.AttributeSets(attSetName)
	Dim value As String = String.Empty
	If Not existingAttSet Is Nothing Then
		If attName = "default" Then
			value = (From oAtt In existingAttSet Select oAtt).FirstOrDefault().Value
		Else
	    	value = (From oAtt In existingAttSet Where oAtt.Name = attName Select oAtt).FirstOrDefault().Value
		End If
	End If
    If value IsNot Nothing Then
        Return value
    Else
        Return String.Empty
    End If
End Function

''' <summary>
''' This method copied from here:
''' https://forums.autodesk.com/t5/inventor-customization/vb-net-find-face-by-face-name/m-p/7950234/highlight/true#M83557
''' </summary>
Public Sub GetNameTest()
    Dim doc As PartDocument = ThisApplication.ActiveDocument
    Dim faceOrEdge As Object = GetNamedEntity(doc, "Brian")
End Sub

''' <summary>
''' Returns a list of objects from the supplied document
''' </summary>
''' <param name="doc"></param>
''' <param name="name"></param>
''' <returns></returns>
Public Function GetNamedGeometry(doc As Document, name As String) As List(Of MatchingGeom)
	Dim listofNamedGeom As List(Of MatchingGeom) = New List(Of MatchingGeom)
	Dim attribMgr As AttributeManager = doc.AttributeManager
    Dim objsFound As ObjectCollection = ThisApplication.TransientObjects.CreateObjectCollection
    objsFound = attribMgr.FindObjects("iLogicEntityNameSet", "iLogicEntityName", name)
	If Not objsFound.Count = 0 Then
		'debug
'		MessageBox.Show("Count of items found in iLogicEntityNameSet = " & objsFound.Count)
		For i = 1 To objsFound.Count
			listofNamedGeom.Add(New MatchingGeom With {.CheckObj = objsFound.Item(i), .MatchingObj = Nothing}) 'objsFound.Item(i))
		Next i
	End If
	
	If listofNamedGeom.Count > 0 Then
		Return listofNamedGeom
	Else
		Return Nothing
	End If
End Function

''' <summary>
''' This method copied from here:
''' https://forums.autodesk.com/t5/inventor-customization/vb-net-find-face-by-face-name/m-p/7950234/highlight/true#M83557
''' </summary>
''' <param name="doc">Document to search</param>
''' <param name="name">Object To look for</param>
''' <returns></returns>
Public Function GetNamedEntity(doc As Inventor.Document, name As String) As Object
    Dim attribMgr As AttributeManager = doc.AttributeManager
    Dim objsFound As ObjectCollection
    objsFound = attribMgr.FindObjects("iLogicEntityNameSet", "iLogicEntityName", name)
    'debug
'	MessageBox.Show("Count of items found in iLogicEntityNameSet = " & objsFound.Count)
    If objsFound.Count > 0 Then
        Return(objsFound.Item(1))
    Else
        Return(Nothing)
    End If
End Function

Public Class MatchingGeom
	Public CheckObj As Object
	Public MatchingObj As Object
End Class
