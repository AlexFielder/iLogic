Imports System.IO
'Imports Microsoft.office.interop.excel
Private Sub Main()
Call insertdummyfiles
End Sub

Private Sub insertdummyfiles
	'define assembly
	Dim asmDoc As AssemblyDocument
	asmDoc = ThisApplication.ActiveDocument
	Dim DummyFilesArray As New ArrayList 
	Dim ParentColumnStartInt As Integer = 0
	Dim ParentColumnName As String
	Dim ChildColumnsStartInt As Integer = 0
	Dim ChildColumnsStartName As String
	Dim ChildColumnsEndName As String
	'create a transaction to encapsulate all our additions in one undo.
	Dim tr As transaction
	tr = ThisApplication.TransactionManager.StartTransaction( _
		ThisApplication.ActiveDocument, _
		"Create Standard Parts From Excel")
	
	Dim ProjectRootFolder As String = ThisApplication.DesignProjectManager.ActiveDesignProject.WorkspacePath
	Dim excelFilename As String = ProjectRootFolder & "\QuantifiableParts.xlsx"
	'MessageBox.Show(excelfilename)
	
	Dim COTSPrefix As String = "COTS-"
	Dim COTSPartNumStart As Long = 100000
	Dim ItemNo As Integer = 200
	Dim folderbrowser As New System.Windows.Forms.FolderBrowserDialog()
	folderbrowser.RootFolder = ProjectRootFolder
	folderbrowser.Description = "Select Folder to look for files to process."
	folderbrowser.ShowDialog()
	Dim SelectedProjectFolder As String = folderbrowser.selectedpath
	If SelectedProjectFolder Is Nothing Then Exit Sub
	Dim COTSInitialPrefix As String = SelectedProjectFolder & "\" & InputBox("What number do you want to start at?", "Title", CStr(COTSPartNumStart))
	DummyFilesArray = GoExcel.CellValues(excelfilename, filename, "A2", "A11")
	'get iProperties from the XLS file
	For MyRow = 2 To 1000 'index row 2 through 1000
		If GoExcel.CellValue("e" & MyRow) = "" Then
			ItemNo += 100
			ItemNo = GetRoundNum(ItemNo,100)
			Continue For
		End If
		Dim PartNum as String = COTSPRefix & (CInt(COTSInitialPrefix) + ItemNo)
		'GoExcel.CellValue("B" & MyRow)	'PART NUMBER
		Dim Quantity As String = GoExcel.CellValue("C" & MyRow)	'UNIT QUANTITY
		Dim Description As String = GoExcel.CellValue("F" & MyRow) & " - " & GoExcel.CellValue("H" & MyRow) 'DESIGNATION & " - " & DESCRIPTION
        'Dim iProp6 as String = GoExcel.CellValue("F" & MyRow)	'VENDOR
        'Dim iProp7 as String = GoExcel.CellValue("G" & MyRow)	'REV
        'Dim iProp8 as String = GoExcel.CellValue("H" & MyRow)	'COMMENTS
        'Dim ItemNo As String = GoExcel.CellValue("I" & MyRow)	'ITEM NUMBER
        'Dim iProp10 as String = GoExcel.CellValue("K" & MyRow)	'SUBJECT/LEGACY DRAWING NUMBER
        Dim occs As ComponentOccurrences
		occs = asmDoc.ComponentDefinition.Occurrences
		'sets up a Matrix based on the origin of the Assembly - we could translate each insert away from 0,0,0 but there's no real need to do that.
		Dim PosnMatrix As Matrix
		PosnMatrix = ThisApplication.TransientGeometry.CreateMatrix
        Dim basefilename = ProjectFolder & "\Graitec\DT-PINK_DISC-000.ipt"
        Dim newfilename As String = ProjectFolder & "\" & PartNum & ".ipt"
        '		MessageBox.Show(newfilename, "Title") 'for debuggering!
        '		Exit Sub
        If Not System.io.file.Exists(newfilename) Then 'we need to create it
			System.io.file.copy(basefilename,newfilename)
		End If
			'creates a componentoccurence object
		Dim realOcc as ComponentOccurrence
		'and adds it at the origin of the assembly.
		realOcc= occs.Add(newfilename,PosnMatrix)
		Dim realOccStr As String = realOcc.Name
		'Assign iProperties
		iProperties.Value(realOccStr , "Project", "Description") = iProp5
		iProperties.Value(realOccStr , "Project", "Part Number") = "COTS-" & iProp2
		iProperties.Value(realOccStr , "Project", "Revision Number") = iProp7
		iProperties.Value(realOccStr , "Project", "Vendor") = iProp6
		iProperties.Value(realOccStr , "Summary", "Comments") = GoExcel.CellValue("J" & MyRow) & " BASED ON: " & filename & " PARTS LIST ITEM NUMBER: " & iProp9 & " COMMENTS: " & iProp8
		
		
		If iProp10 = "" Then
			iProperties.Value(realOccStr , "Summary", "Subject") = iProperties.Value("Summary", "Subject") 'sets the Subject iProperty to that of the current Assembly
			iProperties.Value(realOccStr , "Summary", "Title") = iProperties.Value("Summary", "Title") 'sets the title iProperty to that of the current Assembly
		Else
			iProperties.Value(realOccStr , "Summary", "Subject") = iProp10 'sets the Subject iProperty to that of the current row if there is one.
			iProperties.Value(realOccStr , "Summary", "Title") = iProp5 'sets the title iProperty to that of the current row if there is one.
		End If
		'End Assign iProperties
	
		realOcc.Visible = False 'hide the first instance
		Dim index As Integer
		index = 2
		Do While index <= Quantity
		Dim tmpOcc as ComponentOccurrence
			tmpOcc = occs.AddByComponentdefinition(realOcc.Definition,PosnMatrix)
			tmpOcc.Visible = False ' and all subsequent occurrences.
			index += 1
		Loop
		COTSPartNumStart += 1
	Next
tr.End
InventorVb.DocumentUpdate()
End Sub
Private Function GetRoundNum(ByVal Number As Double, ByVal multiple As Integer) As Double
    GetRoundNum = CInt(Number / multiple) * multiple
End Function
