Imports Inventor.ViewOrientationTypeEnum
Imports Inventor.DrawingViewStyleEnum

Private Sub Main
CreateDrawingsFromAssembly(ThisDoc.Document)
End Sub
Private Sub CreateDrawingsFromAssembly(ByVal oDoc as Inventor.Document)
	Dim oDrawingDoc as DrawingDocument    
	Dim oPartDoc as Document
	Dim oSheet As sheet
	Dim oBaseView As DrawingView
	Dim oView1 as DrawingView
	Dim oView2 as DrawingView
	Dim oView3 as DrawingView
	Dim oView4 as DrawingView 

	dim ViewScale as double = 1/10

	dwgQuery=MsgBox("Would you like to Create drawings from this Assembly?", vbYesNo,"Drawing Selection")
	
	If dwgQuery = vbYes Then
		Dim oAssy As Inventor.AssemblyDocument
    	Dim oComp As Inventor.ComponentOccurrence
    	Dim oSubDoc As Inventor.Document

    	Dim NodeName() As String
	    Dim InstNum As String

		If oDoc.DocumentType = Inventor.DocumentTypeEnum.kAssemblyDocumentObject Then
			oAssy = CType(oDoc, AssemblyDocument)

			For Each refDoc As Document In oAssy.AllReferencedDocuments
				If refDoc.FullFileName.Contains("Content Center") Then Continue For
				'Define dwg Template File Location
				oDrawingDoc = ThisApplication.Documents.Add(DocumentTypeEnum.kDrawingDocumentObject, TemplateFileName:= ThisApplication.FileManager.GetTemplateFile(DocumentTypeEnum.kDrawingDocumentObject), CreateVisible:= True)
				oSheet = oDrawingDoc.Sheets.Item(1)
    
				'Define 2d view bottom left corner points for four views
				oPoint1 = ThisApplication.TransientGeometry.CreatePoint2d(11, 11) 'BASE
				oPoint2 = ThisApplication.TransientGeometry.CreatePoint2d(28, 11) 'RIGHT
				oPoint3 = ThisApplication.TransientGeometry.CreatePoint2d(11, 20) 'TOP
				oPoint4 = ThisApplication.TransientGeometry.CreatePoint2d(28, 20) 'ISOMETRIC
				'ISOMETRIC?
				'view styles can be: 
				'DrawingViewStyleEnum.kHiddenLineRemovedDrawingViewStyle
				'DrawingViewStyleEnum.kHiddenLineDrawingViewStyle
				'DrawingViewStyleEnum.kShadedDrawingViewStyle
				'DrawingViewStyleEnum.kShadedHiddenLineDrawingViewStyle
				'DrawingViewStyleEnum.kFromBaseDrawingViewStyle
				'
				
				oBaseView = oSheet.DrawingViews.AddBaseView(refDoc,oPoint1, ViewScale,kFrontViewOrientation, DrawingViewStyleEnum.kHiddenLineRemovedDrawingViewStyle)', KTANGENTEDGESON)
    
				oView2 = oSheet.DrawingViews.AddProjectedView(oBaseView,oPoint2, DrawingViewStyleEnum.kFromBaseDrawingViewStyle,ViewScale)
				oView3 = oSheet.DrawingViews.AddProjectedView(oBaseView,oPoint3, DrawingViewStyleEnum.kFromBaseDrawingViewStyle, ViewScale)
				oView4 = oSheet.DrawingViews.AddProjectedView(oBaseView,oPoint4, DrawingViewStyleEnum.kFromBaseDrawingViewStyle, ViewScale)
			Next
	  
		End If
	End If
End Sub
