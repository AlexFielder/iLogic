Option explicit On

Imports System.Linq
Imports System.Collections.Generic
Imports Inventor
Sub Main()
	iLogicVb.UpdateWhenDone = True
	transObjs = ThisApplication.TransientObjects
	transGeom = ThisApplication.TransientGeometry
    Dim oDoc As AssemblyDocument
    oDoc = ThisApplication.ActiveDocument

    Dim oCompdef As AssemblyComponentDefinition
    oCompdef = oDoc.ComponentDefinition

    Dim oBody1 As SurfaceBody
    Dim oBody2 As SurfaceBody
	
	CheckForAndDeleteExistingFolders(oCompdef)
	
    oBody1 = ThisApplication.CommandManager.Pick(SelectionFilterEnum.kPartBodyFilter, "Select first body")
    oBody2 = ThisApplication.CommandManager.Pick(SelectionFilterEnum.kPartBodyFilter, "Select a body to compare")
	
	If oBody1 Is Nothing Or oBody2 Is Nothing Then
		MessageBox.Show("You were supposed to select something, Exiting!", "You broke it!", MessageBoxButtons.OK)
		Exit Sub
	End If
	
'	Dim trans As Transaction = ThisApplication.TransactionManager.StartTransaction(oDoc, "Hole Alignment Check")
'	Try
	    Dim oFace As Face
		Dim newAxes As List(Of WorkAxis) = CheckBodyFaces(oCompdef, oBody1, oBody2)

	    Dim Doc As Document = ThisDoc.Document
		Dim oPane As BrowserPane
	    oPane = Doc.BrowserPanes("Model")
		
		Dim topNode As BrowserNode = oPane.TopNode

		
		
	    Dim alignedNodes As List(Of WorkAxis) = New list(Of WorkAxis) 'ObjectCollection
'	    alignedNodes = ThisApplication.TransientObjects.CreateObjectCollection

	    Dim misAlignedNodes As List(Of WorkAxis) = New list(Of WorkAxis) 'ObjectCollection
'	    misAlignedNodes = ThisApplication.TransientObjects.CreateObjectCollection

		SplitNodeLists(oPane, newAxes, alignedNodes, misAlignedNodes)

	    For Each oAxis As WorkAxis In newAxes
	        Dim misaligned As Boolean = oAxis.Name.EndsWith("misaligned")
			
	        Dim oNode As BrowserNode = oPane.GetBrowserNodeFromObject(oAxis)
			Dim nodeDef As NativeBrowserNodeDefinition = oNode.BrowserNodeDefinition
			
			
	        If misaligned = True Then
	            misAlignedNodes.Add(oAxis)
	        Else
				alignedNodes.Add(oAxis)
	        End If
	    Next
		
		AddNewAxesToBrowserFolders(alignedNodes, misAlignedNodes, oPane, topNode)
		'works but takes time
'		oDoc.Rebuild()
		oDoc.Update()
		'does nothing
	    'oPane.Refresh()
'	Catch ex As Exception
'		MessageBox.Show("There was an error!" & vbCrLf & ex.Message, "Danger Will Robinson")
'		trans.Abort
'		Exit Sub
'	Finally
'		If Not trans Is Nothing Then
'			trans.End()
'		End If
'	End Try
End Sub

Function CheckBodyFaces(ByVal oCompDef As AssemblyComponentDefinition, ByVal oBody1 As SurfaceBody, ByVal oBody2 As SurfaceBody) As List(Of WorkAxis)
	Dim axisList As List(Of WorkAxis) = New List(Of WorkAxis)
	Dim oAxis As WorkAxis
	For Each oFace As Face In oBody1.Faces
        If oFace.SurfaceType = SurfaceTypeEnum.kCylinderSurface Then
            oAxis = oCompDef.WorkAxes.AddFixed(oFace.Geometry.BasePoint, oFace.Geometry.AxisVector)
            Dim comparedFace As Face
            comparedFace = CompareFaces(oAxis, oBody2, oCompDef)

            If comparedFace Is Nothing Then
				'set oface color to red here
                oAxis.Name = oAxis.Name & "_misaligned"
            Else
                Dim oHoleFeature1 As HoleFeature
				Dim oHoleFeature2 As HoleFeature
				Dim dia1 As Double
				Dim dia2 As Double
				
				If TypeOf oFace.CreatedByFeature Is HoleFeature Then
                	oHoleFeature1 = oFace.CreatedByFeature
	                dia1 = oHoleFeature1.HoleDiameter.Value
	                dia1 = dia1 * 10 'Converting cm to mm
				Else
					Debug.Print(oFace.CreatedByFeature.Type.ToString())
				End If
				
				If oHoleFeature1 Is Nothing Then Continue For
                
				If TypeOf comparedFace.CreatedByFeature Is HoleFeature Then ' there's nothing to compare
                	oHoleFeature2 = comparedFace.CreatedByFeature
	                dia2 = oHoleFeature2.HoleDiameter.Value
	                dia2 = dia2 * 10 'Converting cm to mm

	                If Math.Round(dia1, 4) = Math.Round(dia2, 4) Then
						'set face color = green
	                    Debug.Print("Hole diameter of plate 1 = " & dia1 & " compared with Hole diameter of plate 2 = " & dia2 & " => OK - Default")
						oAxis.name = oAxis.Name & "_aligned_green"
	                ElseIf Math.Round(dia1, 4) >= Math.Round(dia2, 4) And Math.Round(dia1, 4) <= Math.Round(dia2, 4) + 0.5 Then
						'set face color = orange
	                    Debug.Print("Hole diameter of plate 1 = " & dia1 & " compared with Hole diameter of plate 2 = " & dia2 & " => OK - Special Type")
						oAxis.name = oAxis.Name & "_aligned_amber"
	                Else
						'set face color = red
	                    Debug.Print("Hole diameter of plate 1 = " & dia1 & " compared with Hole diameter of plate 2 = " & dia2 & " => Not OK")
						oAxis.name = oAxis.Name & "_aligned_red"
	                End If
				Else
					Debug.Print(oFace.CreatedByFeature.Type.ToString())
					oAxis.name = oAxis.Name & "_aligned_unknown"
				End If
            End If
			axisList.Add(oAxis)
        End If
    Next
	
	Return axisList
End Function

Sub SplitNodeLists(ByVal oPane As BrowserNode, ByVal newAxes As List(Of WorkAxis), ByRef alignedNodes As List(Of WorkAxis), ByRef misAlignedNodes As List(Of WorkAxis))
	For Each oAxis As WorkAxis In newAxes
        Dim misaligned As Boolean = oAxis.Name.EndsWith("misaligned")
		
        Dim oNode As BrowserNode = oPane.GetBrowserNodeFromObject(oAxis)
		Dim nodeDef As NativeBrowserNodeDefinition = oNode.BrowserNodeDefinition
		
		
        If misaligned = True Then
            misAlignedNodes.Add(oAxis)
        Else
			alignedNodes.Add(oAxis)
        End If
    Next
End Sub

''' <summary>
''' 
''' </summary>
''' <param name="alignedNodes"></param>
''' <param name="misAlignedNodes"></param>
''' <param name="oPane"></param>
''' <param name="topNode"></param>
Sub AddNewAxesToBrowserFolders(ByVal alignedNodesList As List(Of WorkAxis), ByVal misAlignedNodesList As List(Of WorkAxis), 
								ByVal oPane As BrowserPane, ByVal topNode As BrowserNode)
	Dim alignedAxes As BrowserFolder = (From folder As BrowserFolder In topNode.BrowserFolders
																	Where folder.name = "Aligned Axes"
																	Select folder).FirstOrDefault()
'break
	Dim alignedNodes As ObjectCollection = transObjs.CreateObjectCollection
	If alignedAxes Is Nothing Then
		For Each axis As WorkAxis In alignedNodesList
			alignedNodes.Add(oPane.GetBrowserNodeFromObject(axis))
		Next
    	alignedAxes = oPane.AddBrowserFolder("Aligned Axes", alignedNodes)
'	Else
'		Dim lastAlignedAxisNode As BrowserNode = alignedAxes.BrowserNode.BrowserNodes(alignedAxes.BrowserNode.BrowserNodes.Count)
'		'add existing browsernodes to the new collection because the Inventor API is retarded on this.
'		For Each node As BrowserNode In alignedAxes.BrowserNode.BrowserNodes
'			alignedNodes.Add(node)
'		Next
'		'before deleting and recreating the BrowserFolder object
'		alignedAxes.Delete
'Break
'		Dim newAlignedAxes As BrowserFolder = oPane.AddBrowserFolder("Aligned Axes", alignedNodes)
	End If

    Dim misAlignedAxes As BrowserFolder = (From folder As BrowserFolder In topNode.BrowserFolders
																Where folder.name = "MisAligned Axes"
																Select folder).FirstOrDefault()
	Dim misAlignedNodes As ObjectCollection = transObjs.CreateObjectCollection
	For Each axis As WorkAxis In misAlignedNodesList
			misAlignedNodes.Add(oPane.GetBrowserNodeFromObject(axis))
		Next
	If misAlignedAxes Is Nothing Then
    	misAlignedAxes = oPane.AddBrowserFolder("MisAligned Axes", misAlignedNodes)
'	Else
'		'add existing browsernodes to the new collection because the Inventor API is retarded on this.
'		For Each node As BrowserNode In misAlignedAxes.BrowserNode.BrowserNodes
'			misAlignedNodes.Add(node)
'		Next
'		misAlignedAxes.Delete
'Break
'		Dim newMisAlignedAxes As BrowserFolder = oPane.AddBrowserFolder("MisAligned Axes", misAlignedNodes)
	End If
End Sub

Public transObjs As TransientObjects = Nothing
Public transGeom As TransientGeometry = Nothing

Sub CheckForAndDeleteExistingFolders(ByVal Compdef As AssemblyComponentDefinition)
		Dim oDoc As Document = ThisDoc.Document
		Dim oPane As BrowserPane
	    oPane = oDoc.BrowserPanes("Model")
		Dim topNode As BrowserNode = oPane.TopNode
		
		Dim deleteExistingAxesAndFolders As Boolean = False
		'this check is currently removed because adding existing workaxes to a new folder doesn't work for some reason.
		'If MessageBox.Show("Delete any existing folders/alignment axes?", "reset alignment", MessageBoxButtons.YesNo) = DialogResult.Yes Then
			Dim misAlignedAxesFolder As BrowserFolder = (From folder As BrowserFolder In topNode.BrowserFolders
															Where folder.name = "MisAligned Axes"
															Select folder).FirstOrDefault()
			If Not misAlignedAxesFolder Is Nothing Then
				misAlignedAxesFolder.Delete
			End If
			
			Dim misaligned As List(Of WorkAxis) = (From axis As WorkAxis In Compdef.workaxes
													Where axis.name.endswith("misaligned")
													Select axis).tolist()
			If Not misaligned Is Nothing Then
				For Each axis As WorkAxis In misaligned
					axis.Delete()
				Next
			End If
			
		    Dim alignedAxesFolder As BrowserFolder = (From folder As BrowserFolder In topNode.BrowserFolders
															Where folder.name = "Aligned Axes"
															Select folder).FirstOrDefault()
			If Not alignedAxesFolder Is Nothing Then
				For Each onode As BrowserNode In alignedAxesFolder.BrowserNode.BrowserNodes
					If TypeOf onode.NativeObject Is WorkAxis Then
						Dim deleteAxis As WorkAxis = onode.NativeObject
						deleteAxis.Delete
					End If
				Next
				alignedAxesFolder.Delete
			End If
		'End If
End Sub

Public Function CompareFaces(ByVal oAxis1 As WorkAxis, ByVal oBody As SurfaceBody, ByVal compDef As AssemblyComponentDefinition) As Face
    For Each oFace As Face In oBody.Faces
        If oFace.SurfaceType = SurfaceTypeEnum.kCylinderSurface Then
            Dim oAxis As WorkAxis

            oAxis = compDef.WorkAxes.AddFixed(oFace.Geometry.BasePoint, oFace.Geometry.AxisVector)

            If oAxis.Line.IsColinearTo(oAxis1.Line) Then
                oAxis.Delete()
                Return oFace
                Exit Function
            Else
                oAxis.Delete()
            End If
        End If
    Next
    Return Nothing
End Function

''' <summary>
''' Does what it says on the tin
''' </summary>
''' <param name="colourname"></param>
''' <returns></returns>
Public Function GetColourFromString(ByVal colourname As String) As Color
	colourname = colourname.ToLower()
	Select Case colourname
		Case "black"
			Return transObjs.CreateColor(255, 255, 255)
		Case "red"
			Return transObjs.CreateColor(255, 0, 0)
		Case "green"
			Return transObjs.CreateColor(0, 255, 0)
		Case "orange"
			Return transObjs.CreateColor(255, 165, 0)
		Case "blue"
			Return transObjs.CreateColor(0, 0, 255)
	End Select
End Function
