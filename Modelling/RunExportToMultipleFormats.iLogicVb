Option Explicit On
'Imports System.windows
Imports System.IO
'Runs the export to STEP, IGES, and DXF
Sub Main()
	CurrentPath = System.IO.Path.getdirectoryname(ThisApplication.activedocument.fulldocumentname)
	NewPath = CurrentPath & "\"& System.IO.Path.GetFileNameWithoutExtension(ThisApplication.activedocument.fulldocumentname) & "\"
	'Check for the PDF folder and create it if it does not exist
	If Not System.IO.Directory.Exists(NewPath) Then
    	System.IO.Directory.CreateDirectory(NewPath)
	End If
	'3D
	If ThisApplication.ActiveDocument.DocumentType = DocumentTypeEnum.kAssemblyDocumentObject Or ThisApplication.ActiveDocument.DocumentType = DocumentTypeEnum.kPartDocumentObject Then
		ExportSAT()
		ExportIGES()
		ExportSTEP()
		
		ExportDXF()
		'only runs when >=2017 release product is used.
		Export3DPDF()
		'only runs if the file is a sheet metal part!
		ExportFlatPatternDXF()
		'2D
	Else If ThisApplication.ActiveDocument.DocumentType = DocumentTypeEnum.kAssemblyDocumentObject Then
		ExportDXF()
		Export3DPDF()
	else if ThisApplication.ActiveDocument.DocumentType = DocumentTypeEnum.kDrawingdocumentobject then
		ExportPDF()
	End If
	Dim result As DialogResult = MessageBox.Show("Want to Attach exported files?", "Say, Yes Ben.", MessageBoxButtons.YesNoCancel)
	If result = vbYes Then
		AddReferences(ThisApplication.ActiveDocument,NewPath)
	End If
End Sub

'A COUPLE OF GLOBAL VARIABLES
Public CurrentPath As String = ""
Public NewPath As String = ""

'This is a modified copy of the built-in snippet
Public Sub ExportSAT()
	' Set reference to active document.
	Dim oDoc as document = ThisApplication.ActiveDocument
	' Get document's full file name
	'sFname = ThisDoc.PathAndFileName(False) & ".sat"
	Dim sFname As String = NewPath & System.IO.Path.GetFileNameWithoutExtension(ThisApplication.activedocument.fulldocumentname) & ".sat"
	oDoc.SaveAs(sFname, True)
End Sub

'This is a modified copy of the built-in snippet
Public Sub ExportIGES()
	' Get the IGES translator Add-In.
	Dim oIGESTranslator As TranslatorAddIn
	oIGESTranslator = ThisApplication.ApplicationAddIns.ItemById("{90AF7F44-0C01-11D5-8E83-0010B541CD80}")
	Dim oContext As TranslationContext
	oContext = ThisApplication.TransientObjects.CreateTranslationContext
	Dim oOptions As NameValueMap
	oOptions = ThisApplication.TransientObjects.CreateNameValueMap
	If oIGESTranslator.HasSaveCopyAsOptions(ThisApplication.ActiveDocument, oContext, oOptions) Then
		' Set geometry type for wireframe.
		' 0 = Surfaces, 1 = Solids, 2 = Wireframe
		oOptions.Value("GeometryType") = 1
		' To set other translator values:
		' oOptions.Value("SolidFaceType") = n
		' 0 = NURBS, 1 = Analytic
		' oOptions.Value("SurfaceType") = n
		' 0 = 143(Bounded), 1 = 144(Trimmed)
		oContext.Type = IOMechanismEnum.kFileBrowseIOMechanism
		Dim oData As DataMedium
		oData = ThisApplication.TransientObjects.CreateDataMedium
		'oData.FileName = ThisDoc.PathAndFileName(False) & ".igs"
		oData.FileName = NewPath & System.IO.Path.GetFileNameWithoutExtension(ThisApplication.activedocument.fulldocumentname) & ".igs"
		oIGESTranslator.SaveCopyAs(ThisApplication.ActiveDocument, oContext, oOptions, oData)
	End If
End Sub

'This is a modified copy of the built-in snippet
Public Sub ExportSTEP()
	' Get the STEP translator Add-In.
	Dim oSTEPTranslator As TranslatorAddIn
	oSTEPTranslator = ThisApplication.ApplicationAddIns.ItemById("{90AF7F40-0C01-11D5-8E83-0010B541CD80}")
	Dim oContext As TranslationContext
	oContext = ThisApplication.TransientObjects.CreateTranslationContext
	Dim oOptions As NameValueMap
	oOptions = ThisApplication.TransientObjects.CreateNameValueMap
	
	If oSTEPTranslator.HasSaveCopyAsOptions(ThisApplication.ActiveDocument, oContext, oOptions) Then
		' Set application protocol.
		' 2 = AP 203 - Configuration Controlled Design
		' 3 = AP 214 - Automotive Design
		oOptions.Value("ApplicationProtocolType") = 3
		' Other options...
		'oOptions.Value("Author") = ""
		'oOptions.Value("Authorization") = ""
		'oOptions.Value("Description") = ""
		'oOptions.Value("Organization") = ""
		oContext.Type = IOMechanismEnum.kFileBrowseIOMechanism
		Dim oData As DataMedium
		oData = ThisApplication.TransientObjects.CreateDataMedium
		'oData.FileName = ThisDoc.PathAndFileName(False) & ".stp"
		oData.FileName  = NewPath & System.IO.Path.GetFileNameWithoutExtension(ThisApplication.activedocument.fulldocumentname) & ".stp"
		oSTEPTranslator.SaveCopyAs(ThisApplication.ActiveDocument, oContext, oOptions, oData)
	End If
End Sub

'copied from https://forums.autodesk.com/t5/inventor-customization/ilogic-rule-to-ask-yes-or-no-for-dxf-export-when-saving-idw/td-p/3939068
Public Sub 	ExportDXF()
	' Get the DXF translator Add-In.
	'path_and_nameDXF = ThisDoc.PathAndFileName(False)
	Dim DXFAddIn As TranslatorAddIn
	DXFAddIn = ThisApplication.ApplicationAddIns.ItemById("{C24E3AC4-122E-11D5-8E91-0010B541CD80}")
	'Set a reference to the active document (the document to be published).
	Dim oDocument As Document
	oDocument = ThisApplication.ActiveDocument
	Dim oContext As TranslationContext
	oContext = ThisApplication.TransientObjects.CreateTranslationContext
	oContext.Type = IOMechanismEnum.kFileBrowseIOMechanism
	' Create a NameValueMap object
	Dim oOptions As NameValueMap
	oOptions = ThisApplication.TransientObjects.CreateNameValueMap
	' Create a DataMedium object
	Dim oDataMedium As DataMedium
	oDataMedium = ThisApplication.TransientObjects.CreateDataMedium
	'If DXFAddIn.HasSaveCopyAsOptions(oDocument, oContext, oOptions) Then
	'	Dim strIniFile As String
	'	strIniFile = "C:\Users\Farr\Documents\Inventor\DXF_EXPORT_INI\DXF_EXPORT.ini"
	'	oOptions.Value("Export_Acad_IniFile") = strIniFile
	'End If
	oDataMedium.FileName = NewPath & System.IO.Path.GetFileNameWithoutExtension(ThisApplication.activedocument.fulldocumentname) & ".dxf"
	Call DXFAddIn.SaveCopyAs(oDocument, oContext, oOptions, oDataMedium)
End Sub

' copied from here: https://inventorlogicblog.wordpress.com/2016/04/27/autodesk-inventor-ilogic-export-to-3d-pdf-and-attachembed/
' with some simplification because we don't need to attach the resultant pdf at this stage.
Public Sub Export3DPDF()
	If Not ThisApplication.SoftwareVersion.Major >20 Then
		ThisApplication.StatusBarText = ThisApplication.SoftwareVersion.Major
		MessageBox.Show("3D PDF export not available in Inventor versions < 2017 release!")
		Exit Sub
	End If
	' Get the 3D PDF Add-In.
    Dim oPDFAddIn As ApplicationAddIn
    Dim oAddin As ApplicationAddIn
    For Each oAddin In ThisApplication.ApplicationAddIns
        If oAddin.ClassIdString = "{3EE52B28-D6E0-4EA4-8AA6-C2A266DEBB88}" Then
            oPDFAddIn = oAddin
            Exit For
        End If
    Next
    
    If oPDFAddIn Is Nothing Then
        MsgBox("Inventor 3D PDF Addin not loaded.")
        Exit Sub
    End If
    
    Dim oPDFConvertor3D = oPDFAddIn.Automation
    
    'Set a reference to the active document (the document to be published).
    Dim oDocument As Document = ThisApplication.ActiveDocument
    
    If oDocument.FileSaveCounter = 0 Then
        MsgBox("You must save the document to continue...", 64, "My iLogic")
    Return
    End If
    
    ' Create a NameValueMap objectfor all options...
    Dim oOptions As NameValueMap = ThisApplication.TransientObjects.CreateNameValueMap
    Dim STEPFileOptions As NameValueMap = ThisApplication.TransientObjects.CreateNameValueMap
    
    ' All Possible Options
    ' Export file name and location...
    oOptions.Value("FileOutputLocation") = NewPath & System.IO.Path.GetFileNameWithoutExtension(ThisApplication.activedocument.fulldocumentname) & ".pdf"
    ' Export annotations?
    oOptions.Value("ExportAnnotations") = 1
    ' Export work features?
    oOptions.Value("ExportWokFeatures") = 1
    ' Attach STEP file to 3D PDF?
    oOptions.Value("GenerateAndAttachSTEPFile") = True
    ' What quality (high quality takes longer to export)
    'oOptions.Value("VisualizationQuality") = AccuracyEnumVeryHigh
    'oOptions.Value("VisualizationQuality") = AccuracyEnum.kHigh
    'oOptions.Value("VisualizationQuality") = AccuracyEnum.kMedium
    oOptions.Value("VisualizationQuality") = AccuracyEnum.kLow
    ' Limit export to entities in selected view representation(s)
    oOptions.Value("LimitToEntitiesInDVRs") = True
    ' Open the 3D PDF when export is complete?
    oOptions.Value("ViewPDFWhenFinished") = False

    ' Export all properties?
    oOptions.Value("ExportAllProperties") = True
    ' OR - Set the specific properties to export
'    Dim sProps(5) As String
'    sProps(0) = "{F29F85E0-4FF9-1068-AB91-08002B27B3D9}:Title"  
'    sProps(1) = "{F29F85E0-4FF9-1068-AB91-08002B27B3D9}:Keywords"  
'    sProps(2) = "{F29F85E0-4FF9-1068-AB91-08002B27B3D9}:Comments" 
'    sProps(3) =    "{32853F0F-3444-11D1-9E93-0060B03C1CA6}:Description"
'    sProps(4) =    "{32853F0F-3444-11D1-9E93-0060B03C1CA6}:Stock Number"
'    sProps(5) =    "{32853F0F-3444-11D1-9E93-0060B03C1CA6}:Revision Number"

    'oOptions.Value("ExportProperties") = sProps
    
    ' Choose the export template based off the current document type
    If oDocument.DocumentType = DocumentTypeEnum.kPartDocumentObject Then
        oOptions.Value("ExportTemplate") = "C:\Users\Public\Documents\Autodesk\Inventor 2017\Templates\Sample Part Template.pdf"
    Else
        oOptions.Value("ExportTemplate") = "C:\Users\Public\Documents\Autodesk\Inventor 2017\Templates\Sample Assembly Template.pdf"
    End If
    
    ' Define a file to attach to the exported 3D PDF - note here I have picked an Excel spreadsheet
    ' You need to use the full path and filename - if it does not exist the file will not be attached.
    Dim oAttachedFiles As String() = {"C:\FileToAttach.xlsx"}
    oOptions.Value("AttachedFiles") = oAttachedFiles
    
    ' Set the design view(s) to export - note here I am exporting only the active design view (view representation)
    Dim sDesignViews(0) As String
    sDesignViews(0) = oDocument.ComponentDefinition.RepresentationsManager.ActiveDesignViewRepresentation.Name
    oOptions.Value("ExportDesignViewRepresentations") = sDesignViews
    
    ' Step file options (if applicable) ==============================
    If oOptions.Value("GenerateAndAttachSTEPFile") = True Then
        STEPFileOptions.Value("ApplicationProtocolType") = 2 '(AP203)
        'STEPFileOptions.Value("ApplicationProtocolType") = 3 '(AP214IS)
        'STEPFileOptions.Value("ApplicationProtocolType") = 4 '(AP242)
        STEPFileOptions.Value("Author") = ThisApplication.UserName
        STEPFileOptions.Value("Authorization") = "Excitech"
        STEPFileOptions.Value("Description") = iProperties.Value("Project", "Description")
        STEPFileOptions.Value("ExportFitTolerance") = 0.001
        STEPFileOptions.Value("IncludeSketches") = False
        STEPFileOptions.Value("Organization") = "Excitech"
        oOptions.Value("STEPFileOptions") = STEPFileOptions
    End If
    ' End of Step file options =======================================
    
    'Publish document.
    Call oPDFConvertor3D.Publish(oDocument, oOptions)
End Sub

'''Prints the selected sheets to multi-page pdf or single sheet pdf file(s).
Public Function ExportPDF(Optional singleSheet As Boolean = False) As String
	Dim oDocument As drawingdocument = ThisApplication.ActiveDocument
	Dim oSheets As Sheets
	Dim oSheet As Sheet
	Dim DrawingNumber As String = String.empty
	Dim DrawingTitle As String = String.empty
	Dim DrawingPrefix As String = String.Empty
	Dim dwgdoc As DrawingDocument = ThisApplication.ActiveDocument
	
	For i = 1 To oDocument.Sheets.Count
		oDocument.Sheets(i).Activate
		osheet = oDocument.Sheets(i)
		'MessageBox.Show(osheet.Name)
		Dim oTitleBlock As TitleBlock = oDocument.Sheets(i).TitleBlock
		For Each oTextBox As Inventor.TextBox In oTitleBlock.Definition.Sketch.TextBoxes
			' MessageBox.Show(otextbox.Text)
			If otextbox.Text <> "" Then
				Select oTextBox.Text
					Case "<Drawing Number>":
						DrawingNumber = oTitleBlock.GetResultText(oTextBox)
					Case "Drawing Prefix": 
						DrawingPrefix = oTitleBlock.GetResultText(oTextBox)
					Case "TITLE":
						DrawingTitle = oTitleBlock.GetResultText(oTextBox)
				End Select
			End If
		Next
		If Not DrawingNumber = String.empty And Not DrawingPrefix = String.empty Then
			PrintSheet(osheet, DrawingNumber, DrawingPrefix, singleSheet)
		Else
			MessageBox.Show("Either the Drawing Number or Prefix was missing on this sheet, Exiting!")
			Exit Function
		End If
	Next
'MessageBox.Show("Done!")
end function

Public Function PrintSheet(ByVal sht As Sheet, ByVal DrawingNum As String, ByVal DrawingPrefix As String, Optional singleSheet As Boolean = False) As String
	Dim oPath As String = ThisDoc.Path
	Dim PN As String = iProperties.Value("Project", "Part Number")

	'path_and_namePDF = ThisDoc.Pathandname(False)
	Dim oFileName As String = ThisDoc.FileName(False) 'without extension
	Dim oPDFAddIn As ApplicationAddIn = ThisApplication.ApplicationAddIns.ItemById("{0AC6FD96-2F4D-42CE-8BE0-8AEA580399E4}")
	Dim oDocument As Document = ThisApplication.ActiveDocument
	Dim oContext As TranslationContext = ThisApplication.TransientObjects.CreateTranslationContext
	oContext.Type = IOMechanismEnum.kFileBrowseIOMechanism
	Dim oOptions As NameValueMap = ThisApplication.TransientObjects.CreateNameValueMap
	Dim oDataMedium As DataMedium = ThisApplication.TransientObjects.CreateDataMedium
	If oPDFAddIn.HasSaveCopyAsOptions(oDocument, oContext, oOptions) Then
		oOptions.Value("All_Color_AS_Black") = 1
		oOptions.Value("Remove_Line_Weights") = 1
		oOptions.Value("Vector_Resolution") = 400
		If singleSheet Then
			oOptions.Value("Sheet_Range") = Inventor.PrintRangeEnum.kPrintCurrentSheet
		Else
			oOptions.Value("Sheet_Range") = Inventor.PrintRangeEnum.kPrintAllSheets 'or whatever this should be!?
		End If
		'oOptions.Value("Custom_Begin_Sheet") = 1
		'oOptions.Value("Custom_End_Sheet") = 4
	End If
	oDataMedium.FileName = oPath & "\" & DrawingNum & " " & DrawingPrefix & ".pdf"
	ThisApplication.StatusBarText = "PDF SAVED TO: " & oDataMedium.FileName
	'MessageBox.Show("PDF SAVED TO: " & oDataMedium.FileName, "PDF Saved", MessageBoxButtons.OK)

	On Error GoTo handlePDFLock
	'Publish document.
	Call oPDFAddIn.SaveCopyAs(oDocument, oContext, oOptions, oDataMedium)
	'--------------------------------------------------------------------------------------------------------------------
	Exit Function
	handlePDFLock: 
	MessageBox.Show("PDF could not be saved, most likely you or someone else has it open", "No PDF for you " & ThisApplication.GeneralOptions.UserName & "!")
	Resume Next
	If System.IO.File.Exists(oDataMedium.FileName) Then
		Return oDataMedium.FileName
	Else
		Return String.Empty
	End If
End function



Public Sub ExportPDF()


End Sub

'copied from here: 
Public Sub ExportFlatPatternDXF()
	If Not ThisApplication.ActiveDocument.DocumentType = DocumentTypeEnum.kPartDocumentObject Then
		Exit Sub
	Else If Not TypeOf ThisApplication.ActiveDocument.ComponentDefinition Is SheetMetalComponentDefinition Then
		Exit Sub
	End If
	
	Dim oDoc As PartDocument
    oDoc = ThisApplication.ActiveDocument
    
	Dim oCompDef As SheetMetalComponentDefinition
    oCompDef = oDoc.ComponentDefinition
    If oCompDef.HasFlatPattern = False Then
	    oCompDef.Unfold
    Else
	    oCompDef.FlatPattern.Edit
    End If

    Dim sOut As String
    sOut = "FLAT PATTERN DXF?AcadVersion=2000&OuterProfileLayer=IV_INTERIOR_PROFILES"

    Dim sFname As String = NewPath & System.IO.Path.GetFileNameWithoutExtension(ThisApplication.activedocument.fulldocumentname) & ".dxf"
    'sFname = ThisDoc.Path & "\" & ThisDoc.FileName(False) & ".dxf"

    MessageBox.Show("DXF SAVED TO: " & sFname ,"DXF Saved", MessageBoxButtons.OK)
    oCompDef.DataIO.WriteDataToFile( sOut, sFname)
	oDoc = ThisApplication.ActiveDocument

	Dim oSMDef As SheetMetalComponentDefinition
	oSMDef = oDoc.ComponentDefinition
	oSMDef.FlatPattern.ExitEdit
End Sub

'copied from here:
Public Sub AddReferences(ByVal odoc as Inventor.Document, ByVal pathToAddFilesFrom As String)
	Dim oleReference As ReferencedOLEFileDescriptor
	Dim dir = New DirectoryInfo(pathToAddFilesFrom)
	For Each file As FileInfo In dir.GetFiles()
		oleReference = odoc.ReferencedOLEFileDescriptors _
			.Add(file.FullName, OLEDocumentTypeEnum.kOLEDocumentLinkObject)
			oleReference.BrowserVisible = True
			oleReference.Visible = False
			oleReference.DisplayName = file.Name
	Next
End Sub
