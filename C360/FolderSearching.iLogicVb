AddReference "System.Core"
AddReference "System.Linq"
'addreference "Microsoft.Win32"

Imports Inventor
Imports System.IO
Imports System.Core
Imports System.Linq
Imports System.Windows.Forms
Imports System.Collections.Generic

Public Sub Main()
    'user feedback tools start
    Try
        Dim sw As New Stopwatch()
        sw.Start()

        Dim IncludeSubFolders As Boolean = True

        Dim ProjectPath As String = ThisApplication.DesignProjectManager.ActiveDesignProject.FullFileName
        ProjectPath = IO.Path.GetDirectoryName(ProjectPath)
        MessageBox.Show(ProjectPath)

        Dim foundFile As FileInfo = GetFileByForEach(ProjectPath, "COTS-100200.ipt")

        If Not foundFile Is Nothing Then
            MessageBox.Show(foundFile.FullName)
        End If

        Dim foundFiles As List(Of FileInfo) = getFilesByWildCard(ProjectPath, "*COTS*")

        If Not foundFiles Is Nothing Then
            If foundFiles.Count > 0 Then
                For i = 0 To foundFiles.Count - 1
                    MessageBox.Show(foundFiles(i).FullName)
                Next
            End If
        Else
            messagebox.show("Found nothing")
        End If

        Dim extensions As String() = {".ipt", ".iam"}
        Dim foundfilesWithLINQ As Ienumerable(Of fileInfo) = GetFilesByLINQWithExclusions(New DirectoryInfo(ProjectPath), "Hinging Bracket", extensions)
        If Not foundfilesWithLINQ Is Nothing Then
            MessageBox.Show(foundfilesWithLINQ.count)
            For Each foundfile As fileinfo In foundfilesWithLINQ
                MessageBox.Show(foundfile.fullname)
            Next
        Else
            MessageBox.Show("Found nothing")
        End If

        sw.Stop()
        Dim timeElapsed As Timespan = sw.elapsed
        MessageBox.Show("Processing took: " & String.Format("{0:00}:{1:00}:{2:00}.{3:00}",
                                                            timeElapsed.Hours,
                                                            timeElapsed.Minutes,
                                                            timeElapsed.Seconds,
                                                            timeElapsed.Milliseconds / 10))
    Catch ex As Exception
        MessageBox.Show(ex.message)
        iProperties.Value("Custom", "C360MessageText_ErrorChecking") = ex.message
        iProperties.Value("Custom", "C360MessageSeverity_ErrorChecking") = "Error"
        iProperties.Value("Custom", "C360MessageTriggered_ErrorChecking") = True
    End Try
End Sub

''' <summary>
''' Searches for one file and returns the System.IO.FileInfo object that represents the file.
''' </summary>
''' <param name="dir"></param>
''' <param name="filename"></param>
''' <returns></returns>
Public Function GetFileByForEach(dir As String, filename As String) As FileInfo
    'search everything
    Dim dirToSearch As DirectoryInfo = New directoryinfo(dir)
    For Each file As FileInfo In dirToSearch.GetFiles(filename, SearchOption.AllDirectories)
        If file.Name = filename Then
            Return file
        End If
    Next
End Function

''' <summary>
''' Performs a wildcard search of the entire folder structure
''' </summary>
''' <param name="dir"></param>
''' <param name="filename"></param>
''' <returns></returns>
Public Function getFilesByWildCard(dir As String, filename As String) As List(Of FileInfo)
    'wildcard search
    Dim dirToSearch As DirectoryInfo = New directoryinfo(dir)
    Dim files As List(Of FileInfo) = New List(Of FileInfo)
    MessageBox.Show(filename)
    For Each file As FileInfo In dirToSearch.GetFiles(filename, SearchOption.AllDirectories)
        'messagebox.show(file.name)
        files.Add(file)
    Next
    Return files
End Function

''' <summary>
''' Searches the given path using a wildcard * surrounding the filename and a string() of file extensions.
''' </summary>
''' <param name="dir">Directory to search</param>
''' <param name="filename">filename to wildcard search</param>
''' <param name="extensions">list of file extensions to search</param>
''' <returns></returns>
Public Function GetFilesByLINQWithExclusions(dir As DirectoryInfo, filename As String, extensions As String()) As IENumerable(Of FileInfo)
    If extensions Is Nothing Then
        Throw New ArgumentNullException("extensions")
    End If
    'Dim files = dir.EnumerateFiles("*.*", SearchOption.AllDirectories).Where(Function(s As FileInfo) Not (s.FullName.Contains("-")) And Not (s.FullName.Contains("OldVersions")))
    'Dim files = dir.EnumerateFiles("*.*", SearchOption.AllDirectories).Where(Function(s As FileInfo) Not (s.FullName.EndsWith(".v")) And Not (s.FullName.contains("OldVersions")))
    Dim files = dir.EnumerateFiles("*" & filename & "*", SearchOption.AllDirectories).Where(Function(s As FileInfo) Not (s.FullName.EndsWith(".v")) And Not (s.FullName.contains("OldVersions")))
    'Return files
    Return files.Where(Function(f As FileInfo) extensions.Contains(f.Extension)).OrderBy(Function(x As FileInfo) x.Name)
End Function
