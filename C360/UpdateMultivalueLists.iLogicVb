Option Explicit On
Sub Main()
	If Not RuleArguments.Exists("ParameterName") Then 'not fired from relevant rule
		MessageBox.Show("This rule only works from the context-sensitive files we need!")
		Exit Sub
	Else
		Dim paramName As String = RuleArguments.Value("ParameterName")
		Dim p As Parameter = Parameter.Param(paramName)
		Logger.Debug(paramName & " updated value = " & p.Value)
		Dim FilterArguments As Inventor.NameValueMap = ThisApplication.TransientObjects.CreateNameValueMap()
		FilterArguments.Value("ParameterValue") = p.Value
		iLogicVb.RunExternalRule("Filter" & paramName, FilterArguments)
	End If
End Sub
