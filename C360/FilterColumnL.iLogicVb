Option Explicit On
Sub main()
	If Not RuleArguments.Exists("ParameterValue") Then
		MessageBox.Show("How did we get here?")
	Else
		'Column L
		Dim paramValue As String = RuleArguments.Value("ParameterValue")
		Dim FilterArguments As Inventor.NameValueMap = ThisApplication.TransientObjects.CreateNameValueMap()
		'this needs to be a list of values to remove/add from the next column along.
		Dim filterList As List(Of String) = New List(Of String)
		Select paramValue
			Case "L"
				filterList.Add("C")
				filterList.Add("K")
				filterList.Add("S")
			Case "R"
				filterList.Add("F")
				filterList.Add("K")
				filterList.Add("M")
				filterList.Add("S")
				filterList.Add("T")
			Case Else
		End Select
		FilterArguments.Value("UniqueValues") = filterList
		FilterArguments.Value("ColumnToFilter") = cNextColumn
		iLogicVb.RunExternalRule("FilterColumnRule", FilterArguments)
	End If
	
End Sub

Public Const cNextColumn As String = "N"
