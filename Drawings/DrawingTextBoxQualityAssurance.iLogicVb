Sub Main()
	oDocument = ThisApplication.ActiveDocument
	Dim oSheets As Sheets
	Dim oPar As UserParameter

	For i = 1 To oDocument.Sheets.Count
		oDocument.Sheets(i).Activate
		oSheet = oDocument.Sheets(i)
		oTitleBlock = oDocument.Sheets(i).TitleBlock
		For Each oTextBox As Inventor.TextBox In oTitleBlock.Definition.Sketch.TextBoxes
			If oTextBox.Text <> "" Then
				CompareTextToExpected(oTextBox, oTitleBlock.GetResultText(oTextBox))
			End If
		Next
	Next
End Sub

Public oDocument As DrawingDocument = Nothing
Public oSheet As Sheet = Nothing
Public oTitleBlock As TitleBlock = Nothing

Function CompareTextToExpected(byval textBox as Inventor.TextBox, byval textBoxContents as string) as Boolean
	select case textBox.Text
		Case "<TITLE>" :
			if not textBoxContents = "your expected string" then MarkTextBoxContentsAsIncorrect(textBox, "Text doesn't match expected Title")
		case "<PART NUMBER>" :
			if not textBoxContents = "your expected string" then MarkTextBoxContentsAsIncorrect(textBox, "Text doesn't match expected Part Number")
	end select
End Function

Sub MarkTextBoxContentsAsIncorrect(byval textbox as Inventor.TextBox, byval ErrorText as string)
	Call CreateText(textbox.Origin, ErrorText)
End Sub

Sub CreateText(ByVal textlocation As Point2d, ByVal QAText As String)
	Call textlocation.transformby(oTitleBlock.Transformation)
	Dim oTG As TransientGeometry = ThisApplication.TransientGeometry
	Dim TextPoint As Point2d = oTG.CreatePoint2d(textLocation.X, textlocation.Y)
	
	Dim oGeneralNotes As GeneralNotes
	oGeneralNotes = oSheet.DrawingNotes.GeneralNotes
	
	Dim oGeneralNote As GeneralNote
	oGeneralNote = oGeneralNotes.AddFitted(TextPoint, QAText)
End Sub
