'Main is always the first method in iLogic if you are working in VB.NET-style code!
Public Sub Main()
ChangeLayerOfOccurrenceCurves()
End Sub

Public Sub ChangeLayerOfOccurrenceCurves() 
   ' Get the active drawing document. 
   Dim drawDoc As DrawingDocument = ThisApplication.ActiveDocument 

   ' Have the user select a drawing view. 
   Dim drawView As DrawingView = ThisApplication.CommandManager.Pick(SelectionFilterEnum.kDrawingViewFilter, "Select a drawing view.")  

   Dim docDesc As DocumentDescriptor = drawView.ReferencedDocumentDescriptor  

   ' Verify that the selected drawing view is of an assembly. 
   If docDesc.ReferencedDocumentType <> DocumentTypeEnum.kAssemblyDocumentObject Then 
      MsgBox "The selected view must be of an assembly." 
      Exit Sub 
   End If  

   ' Get the component definition for the assembly. 
   Dim asmDef As AssemblyComponentDefinition = docDesc.ReferencedDocument.ComponentDefinition  

   ' Process the occurrences, wrapping it in a transaction so the 
   ' entire process can be undone with a single undo operation. 
   Dim trans As Transaction = ThisApplication.TransactionManager.StartTransaction(drawDoc, "Change drawing view color")  

   ' Call the recursive function that does all the work. 
   Call ProcessAssemblyColor(drawView, asmDef.Occurrences) 
   trans.End 
End Sub 



Private Sub ProcessAssemblyColor(drawView As DrawingView, Occurrences As ComponentOccurrences) 
   ' Iterate through the current collection of occurrences. 
   Dim occ As ComponentOccurrence 
   For Each occ In Occurrences 
      ' Check to see if this occurrence is a part or assembly. 
      If occ.DefinitionDocumentType = DocumentTypeEnum.kPartDocumentObject Then 
         ' ** It's a part so process the color.  

         ' Get the render style of the occurrence. 
         Dim color As RenderStyle 
         Dim sourceType As StyleSourceTypeEnum = occ.GetRenderStyle(sourceType)  

         ' Get the TransientsObjects object to use later. 
         Dim transObjs As TransientObjects = ThisApplication.TransientObjects  

         ' Verify that a layer exists for this color. 
         Dim layers As LayersEnumerator = drawView.Parent.Parent.StylesManager.layers  

         Dim drawDoc As DrawingDocument = drawView.Parent.Parent  

         On Error Resume Next 
         Dim colorLayer As Layer = layers.Item(color.Name)  

         If Err.Number <> 0 Then 
            On Error GoTo 0 
            ' Get the diffuse color for the render style. 
            Dim red As Byte 
            Dim green As Byte 
            Dim blue As Byte  

            ' Create a color object that is the diffuse color. 
            Call color.GetDiffuseColor(red, green, blue) 
            Dim newColor As color = transObjs.CreateColor(red, green, blue)  

            ' Copy an arbitrary layer giving it the name 
            ' of the render style. 
            colorLayer = layers.Item(1).Copy(color.Name) 

            ' Set the attributes of the layer to use the color, 
            ' have a solid line type, and a specific width. 
            colorLayer.color = newColor 
            colorLayer.LineType = LineTypeEnum.kContinuousLineType 
            colorLayer.LineWeight = 0.02 
         End If 
         On Error GoTo 0  

         ' Get all of the curves associated with this occurrence. 
         On Error Resume Next 
         Dim drawcurves As DrawingCurvesEnumerator = drawView.DrawingCurves(occ) 
         If Err.Number = 0 Then 
            On Error GoTo 0  

            ' Create an empty collection. 
            Dim objColl As ObjectCollection = transObjs.CreateObjectCollection()  

            ' Add the curve segments to the collection. 
            Dim drawCurve As DrawingCurve 
            For Each drawCurve In drawcurves 
               Dim segment As DrawingCurveSegment 
               For Each segment In drawCurve.Segments 
                  objColl.Add segment 
               Next 
            Next  

            ' Change the layer of all of the segments. 
            Call drawView.Parent.ChangeLayer(objColl, colorLayer) 
         End If 
         On Error GoTo 0 
      Else 
         ' It's an assembly so process its contents. 
         Call ProcessAssemblyColor(drawView, occ.SubOccurrences) 
      End If 
   Next 
End Sub
