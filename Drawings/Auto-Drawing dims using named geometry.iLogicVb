'this rule will attempt to look at a supplied assembly and dimensions the extents of a group of objects that are constrained together.
Sub Main()
    'This rule will create delete any existing iLogic-created dimensions before replacing them anew
    Dim oDWG As DrawingDocument = ThisDoc.Document

    Dim oSht As Sheet = oDWG.ActiveSheet

    Dim oView As DrawingView = ActiveSheet.View("VIEW1").View

    Dim oPart As PartDocument = ActiveSheet.View("VIEW1").ModelDocument

    Dim TransG As TransientGeometry = ThisApplication.TransientGeometry
'break
    Dim oGenDims As GeneralDimensions = oSht.DrawingDimensions.GeneralDimensions

   	Dim datumObjs As ObjectCollection = oPart.AttributeManager.FindObjects("iLogicEntityNameSet", "iLogicEntityName","END01")
	Dim outObjs As ObjectCollection = oPart.AttributeManager.FindObjects("iLogicEntityNameSet", "iLogicEntityName","END02") 'ThisApplication.TransientObjects.CreateObjectCollection

    Dim aoEdge1 As face


'break

    	aoEdge1 = datumObjs.Item(1)
		Break

    Dim aoEdge2 As Face

'break
    aoEdge2 = outObjs.Item(1)

    Dim oDrawCurve1 As DrawingCurve

    oDrawingCurves = oView.DrawingCurves(aoEdge1)
break
    oDrawCurve1 = oDrawingCurves.Item(1)

    Dim oDrawCurve2 As drawingcurve

    oDrawingCurves = oview.DrawingCurves(aoEdge2)
break
    oDrawCurve2 = oDrawingCurves.Item(1)

    Dim oPt1 As Point2d = TransG.Createpoint2d(oView.left + (oView.Width / 4), oView.Top - (oView.Height) - 1)

    messagebox.show("Got dimension line point position: " & oPt1.X.ToString() & "," & oPt1.Y.ToString())

    Dim oDim1 As GeneralDimension = oGenDims.AddLinear(oPt1, oSht.CreateGeometryintent(oDrawCurve1, PointIntentEnum.kStartPointIntent), oSht.CreateGeometryIntent(oDrawCurve2, PointIntentEnum.kEndPointIntent), DimensionTypeEnum.kHorizontalDimensionType)

    messagebox.show("Dimension Added.")

    Dim odimatt1 As Attributeset = oDim1.Attributesets.add("iLogic_Created")

End Sub
